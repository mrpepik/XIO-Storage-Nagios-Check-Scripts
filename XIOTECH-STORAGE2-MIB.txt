-- *****************************************************************
-- XIOTECH-STORAGE2-MIB.txt:
-- *****************************************************************

-- iso.org.dod.internet.private.enterprise.xiotech (1.3.6.1.4.1.2366)

XIOTECH-STORAGE2-MIB DEFINITIONS ::= BEGIN

IMPORTS
        MODULE-IDENTITY, OBJECT-TYPE, OBJECT-IDENTITY, enterprises, 
        Integer32, Unsigned32, Counter64, mib-2, NOTIFICATION-TYPE
                FROM SNMPv2-SMI
        MODULE-COMPLIANCE, OBJECT-GROUP, NOTIFICATION-GROUP
                FROM SNMPv2-CONF
        TEXTUAL-CONVENTION, TimeStamp, DisplayString, DateAndTime, TruthValue, TDomain
		FROM SNMPv2-TC;
				
				
xiotech MODULE-IDENTITY
        LAST-UPDATED    "201007300000Z"
        ORGANIZATION    "IT_Operations"
        CONTACT-INFO
                "Xiotech Corporation
                 Attn: Customer Support
                 Postal: 9950 Federal Drive, Suite 100
                         Colorado Springs, CO 80921
                         USA
                 E-mail: support@xiotech.com"
        DESCRIPTION
                "Initial entries March 2003"
        REVISION        "200603070000Z"
        DESCRIPTION
                "Updated all MIB objects from CLM to SMA"
        REVISION        "201007300000Z"
        DESCRIPTION
                "Updated Trap definitions to include new CEL (System) Events"    
        REVISION        "201104150000Z"
        DESCRIPTION
                "Updated MIB for ISE2.  Removed Battery, added SuperCap"               
        
        ::= { enterprises 2366 }   -- Assigned by IANA  1.3.6.1.4.1.2366
			       
 
xiotechAdvStorArch OBJECT-IDENTITY
	     STATUS  current
	     DESCRIPTION
		    "Definition for xiotechAdvStorArch"
	::= { xiotech 6 }        -- 1.3.6.1.4.1.2366.6
 
iseProducts OBJECT-IDENTITY
	     STATUS  current
	     DESCRIPTION
		    "Definition for iseProducts"
	::= { xiotechAdvStorArch 1 }        -- 1.3.6.1.4.1.2366.6.1
 
iseStorage2 OBJECT-IDENTITY
	     STATUS  current
	     DESCRIPTION
		    "Xiotech ASG Intelligent Storage Element 2"
	::= { iseProducts 2 }        -- 1.3.6.1.4.1.2366.6.1.2
 

iseObjects       OBJECT IDENTIFIER	::= { iseStorage2 1 }   -- 1.3.6.1.4.1.2366.6.1.2.1

iseGeneral       OBJECT IDENTIFIER	::= { iseStorage2 2 }   -- 1.3.6.1.4.1.2366.6.1.2.2
iseNotification  OBJECT IDENTIFIER	::= { iseStorage2 3 }   -- 1.3.6.1.4.1.2366.6.1.2.3
iseConformance   OBJECT IDENTIFIER	::= { iseStorage2 4 }   -- 1.3.6.1.4.1.2366.6.1.2.4

iseAgent         OBJECT IDENTIFIER	::= { iseObjects 1 }   -- 1.3.6.1.4.1.2366.6.1.2.1.1
ise              OBJECT IDENTIFIER  ::= { iseObjects 2 }   -- 1.3.6.1.4.1.2366.6.1.2.1.2
iseMrcs          OBJECT IDENTIFIER	::= { iseObjects 3 }   -- 1.3.6.1.4.1.2366.6.1.2.1.3
iseDataPacs      OBJECT IDENTIFIER	::= { iseObjects 4 }   -- 1.3.6.1.4.1.2366.6.1.2.1.4
iseStoragePools  OBJECT IDENTIFIER  ::= { iseObjects 5 }   -- 1.3.6.1.4.1.2366.6.1.2.1.5 
isePowerSupplies OBJECT IDENTIFIER	::= { iseObjects 6 }   -- 1.3.6.1.4.1.2366.6.1.2.1.6
iseSuperCaps     OBJECT IDENTIFIER	::= { iseObjects 7 }   -- 1.3.6.1.4.1.2366.6.1.2.1.7
iseStorageVols   OBJECT IDENTIFIER	::= { iseObjects 8 }   -- 1.3.6.1.4.1.2366.6.1.2.1.8
iseStorageHosts  OBJECT IDENTIFIER	::= { iseObjects 9 }   -- 1.3.6.1.4.1.2366.6.1.2.1.9
iseFcPorts       OBJECT IDENTIFIER	::= { iseObjects 10 }   -- 1.3.6.1.4.1.2366.6.1.2.1.10
iseSfps          OBJECT IDENTIFIER	::= { iseObjects 11 }   -- 1.3.6.1.4.1.2366.6.1.2.1.11


-- ************** ise ******************
-- ise         OBJECT IDENTIFIER	::= { iseObjects 2 }  - 1.3.6.1.4.1.2366.6.1.2.1.2

iseSerialNum OBJECT-TYPE
	SYNTAX		DisplayString
	MAX-ACCESS 	read-only
	STATUS 		current
	DESCRIPTION	
	 "ISE Serial Number"
	::= { ise 1 }    -- 1.3.6.1.4.1.2366.6.1.2.1.2.1

iseModel    OBJECT-TYPE
	SYNTAX		DisplayString
	MAX-ACCESS 	read-only
	STATUS 		current
	DESCRIPTION	
	 "ISE Model"
	::= { ise 2 }    -- 1.3.6.1.4.1.2366.6.1.2.1.2.2

iseVendor    OBJECT-TYPE
	SYNTAX		DisplayString
	MAX-ACCESS 	read-only
	STATUS 		current
	DESCRIPTION	
	 "ISE Vendor"
	::= { ise 3 }    -- 1.3.6.1.4.1.2366.6.1.2.1.2.3

iseManufacturer    OBJECT-TYPE
	SYNTAX		DisplayString
	MAX-ACCESS 	read-only
	STATUS 		current
	DESCRIPTION	
	 "ISE Manufacturer"
	::= { ise 4 }    -- 1.3.6.1.4.1.2366.6.1.2.1.2.4

iseProductVersion    OBJECT-TYPE
	SYNTAX		DisplayString
	MAX-ACCESS 	read-only
	STATUS 		current
	DESCRIPTION	
	 "ISE Product Version"
	::= { ise 5 }    -- 1.3.6.1.4.1.2366.6.1.2.1.2.5
	
iseWWN    OBJECT-TYPE
	SYNTAX		DisplayString
	MAX-ACCESS 	read-only
	STATUS 		current
	DESCRIPTION	
	 "ISE WWN"
	::= { ise 6 }    -- 1.3.6.1.4.1.2366.6.1.2.1.2.6
		
iseName    OBJECT-TYPE
	SYNTAX		DisplayString
	MAX-ACCESS 	read-only
	STATUS 		current
	DESCRIPTION	
	 "ISE Name"
	::= { ise 7 }    -- 1.3.6.1.4.1.2366.6.1.2.1.2.7


iseStatus OBJECT-TYPE 
	SYNTAX		INTEGER
                {
                  success(0),
                  failure(1),
                  opInProgress(2),
                  prevTaskActive(3),
                  noResources(4),
				          lunBusy(5),
                  invalidID(6),
                  unknownHostType(7),
				          quotaExceeded(8),
                  unknownPool(9),
                  unknownISE(10),
                  invalidCmd(11),
                  unknownTaskID(12),
                  unknownLdOID(13),
                  unknownHbaOID(14),
                  unknownLUN(15),
                  iseUninitialized(16),        -- uninitialzed
                  iseInitialized(17),          -- initialized but no pools configured
				          iseOperational(18)           -- initialized and have pools
                 }
	MAX-ACCESS 	read-only
	STATUS 		current
	DESCRIPTION	
	 "ISE Operational Status"
	::= { ise 8 }	-- 1.3.6.1.4.1.2366.6.1.2.1.2.8

iseStatusDetails    OBJECT-TYPE
	SYNTAX		Integer32
	MAX-ACCESS 	read-only
	STATUS 		current
	DESCRIPTION	
	 "ISE Status Details"
	::= { ise 9 }    -- 1.3.6.1.4.1.2366.6.1.2.1.2.9
	
isePhysicalLocation    OBJECT-TYPE
	SYNTAX		DisplayString
	MAX-ACCESS 	read-only
	STATUS 		current
	DESCRIPTION	
	 "ISE Physical Location"
	::= { ise 10 }    -- 1.3.6.1.4.1.2366.6.1.2.1.2.10

iseAddress    OBJECT-TYPE
	SYNTAX		DisplayString
	MAX-ACCESS 	read-only
	STATUS 		current
	DESCRIPTION	
	 "ISE Address"
	::= { ise 11 }    -- 1.3.6.1.4.1.2366.6.1.2.1.2.11

iseAdminName    OBJECT-TYPE
	SYNTAX		DisplayString
	MAX-ACCESS 	read-only
	STATUS 		current
	DESCRIPTION	
	 "ISE Administrative Contact Name"
	::= { ise 12 }    -- 1.3.6.1.4.1.2366.6.1.2.1.2.12


iseAdminPhone    OBJECT-TYPE
	SYNTAX		DisplayString
	MAX-ACCESS 	read-only
	STATUS 		current
	DESCRIPTION	
	 "ISE Administrative Contact Phone"
	::= { ise 13 }    -- 1.3.6.1.4.1.2366.6.1.2.1.2.13
	

iseAdminEmail    OBJECT-TYPE
	SYNTAX		DisplayString
	MAX-ACCESS 	read-only
	STATUS 		current
	DESCRIPTION	
	 "ISE Administrative Contact Email"
	::= { ise 14 }    -- 1.3.6.1.4.1.2366.6.1.2.1.2.14

iseSpareLevel    OBJECT-TYPE
	SYNTAX		Integer32
	MAX-ACCESS 	read-only
	STATUS 		current
	DESCRIPTION	
	 "ISE Spare Level"
	::= { ise 15 }    -- 1.3.6.1.4.1.2366.6.1.2.1.2.15

iseIpAddress1    OBJECT-TYPE
	SYNTAX		DisplayString
	MAX-ACCESS 	read-only
	STATUS 		current
	DESCRIPTION	
	 "ISE Ip Address 1"
	::= { ise 16 }    -- 1.3.6.1.4.1.2366.6.1.2.1.2.16

iseSubnetMask1    OBJECT-TYPE
	SYNTAX		DisplayString
	MAX-ACCESS 	read-only
	STATUS 		current
	DESCRIPTION	
	 "ISE Subnet Mask 1"
	::= { ise 17 }    -- 1.3.6.1.4.1.2366.6.1.2.1.2.17	
		
iseGateway1   OBJECT-TYPE
	SYNTAX		DisplayString
	MAX-ACCESS 	read-only
	STATUS 		current
	DESCRIPTION	
	 "ISE Gateway 1"
	::= { ise 18 }    -- 1.3.6.1.4.1.2366.6.1.2.1.2.18
	
iseHostName1    OBJECT-TYPE
	SYNTAX		DisplayString
	MAX-ACCESS 	read-only
	STATUS 		current
	DESCRIPTION	
	 "ISE Host Name 1"
	::= { ise 19}    -- 1.3.6.1.4.1.2366.6.1.2.1.2.19

iseHardwareAddress1    OBJECT-TYPE
	SYNTAX		DisplayString
	MAX-ACCESS 	read-only
	STATUS 		current
	DESCRIPTION	
	 "ISE Hardware Address (MAC)"
	::= { ise 20 }    -- 1.3.6.1.4.1.2366.6.1.2.1.2.20
	
iseNetworkSpeed1    OBJECT-TYPE
	SYNTAX		Integer32
	MAX-ACCESS 	read-only
	STATUS 		current
	DESCRIPTION	
	 "ISE - Speed of the Network"
	::= { ise 21 }    -- 1.3.6.1.4.1.2366.6.1.2.1.2.21
	

iseIpAddress2    OBJECT-TYPE
	SYNTAX		DisplayString
	MAX-ACCESS 	read-only
	STATUS 		current
	DESCRIPTION	
	 "ISE Ip Address 2"
	::= { ise 22 }    -- 1.3.6.1.4.1.2366.6.1.2.1.2.22

iseSubnetMask2    OBJECT-TYPE
	SYNTAX		DisplayString
	MAX-ACCESS 	read-only
	STATUS 		current
	DESCRIPTION	
	 "ISE Subnet Mask 2"
	::= { ise 23 }    -- 1.3.6.1.4.1.2366.6.1.2.1.2.23	
		
iseGateway2   OBJECT-TYPE
	SYNTAX		DisplayString
	MAX-ACCESS 	read-only
	STATUS 		current
	DESCRIPTION	
	 "ISE Gateway 2"
	::= { ise 24 }    -- 1.3.6.1.4.1.2366.6.1.2.1.2.24
	
iseHostName2    OBJECT-TYPE
	SYNTAX		DisplayString
	MAX-ACCESS 	read-only
	STATUS 		current
	DESCRIPTION	
	 "ISE Host Name 2"
	::= { ise 25}    -- 1.3.6.1.4.1.2366.6.1.2.1.2.25

iseHardwareAddress2    OBJECT-TYPE
	SYNTAX		DisplayString
	MAX-ACCESS 	read-only
	STATUS 		current
	DESCRIPTION	
	 "ISE Hardware Address (MAC) 2"
	::= { ise 26 }    -- 1.3.6.1.4.1.2366.6.1.2.1.2.26
	
iseNetworkSpeed2    OBJECT-TYPE
	SYNTAX		Integer32
	MAX-ACCESS 	read-only
	STATUS 		current
	DESCRIPTION	
	 "ISE - Speed of Network 2"
	::= { ise 27 }    -- 1.3.6.1.4.1.2366.6.1.2.1.2.27
	
iseLinkUp    OBJECT-TYPE
	SYNTAX		DisplayString
	MAX-ACCESS 	read-only
	STATUS 		current
	DESCRIPTION	
	 "ISE is Link Up?"
	::= { ise 28 }    -- 1.3.6.1.4.1.2366.6.1.2.1.2.28

iseFullDuplex    OBJECT-TYPE
	SYNTAX		DisplayString
	MAX-ACCESS 	read-only
	STATUS 		current
	DESCRIPTION	
	 "ISE is Full Duplex?"
	::= { ise 29 }    -- 1.3.6.1.4.1.2366.6.1.2.1.2.29
	
iseDHCPEnabled    OBJECT-TYPE
	SYNTAX		DisplayString
	MAX-ACCESS 	read-only
	STATUS 		current
	DESCRIPTION	
	 "ISE is DHCP Enabled?"
	::= { ise 30 }    -- 1.3.6.1.4.1.2366.6.1.2.1.2.30
	
iseWOLEnabled    OBJECT-TYPE
	SYNTAX		DisplayString
	MAX-ACCESS 	read-only
	STATUS 		current
	DESCRIPTION	
	 "ISE is Wake On LAN Enabled?"
	::= { ise 31 }    -- 1.3.6.1.4.1.2366.6.1.2.1.2.31	

iseTemperature    OBJECT-TYPE
	SYNTAX		Integer32
	MAX-ACCESS 	read-only
	STATUS 		current
	DESCRIPTION	
	 "ISE Temperature"
	::= { ise 32 }    -- 1.3.6.1.4.1.2366.6.1.2.1.2.32

iseTotalVolumes    OBJECT-TYPE
	SYNTAX		Integer32
	MAX-ACCESS 	read-only
	STATUS 		current
	DESCRIPTION	
	 "ISE Total number of Volumes"
	::= { ise 33 }    -- 1.3.6.1.4.1.2366.6.1.2.1.2.33

iseTotalHosts    OBJECT-TYPE
	SYNTAX		Integer32
	MAX-ACCESS 	read-only
	STATUS 		current
	DESCRIPTION	
	 "ISE Total number of Hosts"
	::= { ise 34 }    -- 1.3.6.1.4.1.2366.6.1.2.1.2.34
	
	iseStatusStr    OBJECT-TYPE
	SYNTAX		DisplayString
	MAX-ACCESS 	read-only
	STATUS 		current
	DESCRIPTION	
	 "ISE Status String - a string expressing the current condition"
	::= { ise 35 }    -- 1.3.6.1.4.1.2366.6.1.2.1.2.35
	
	iseStatusDetailsStr    OBJECT-TYPE
	SYNTAX		DisplayString
	MAX-ACCESS 	read-only
	STATUS 		current
	DESCRIPTION	
	 "ISE Status Details String - a string expressing the current condition in detail"
	::= { ise 36 }    -- 1.3.6.1.4.1.2366.6.1.2.1.2.36
	

-- ************** MRC 1 **************

mrc1 OBJECT IDENTIFIER    ::= { iseMrcs 1 } -- 1.3.6.1.4.1.2366.6.1.2.1.3.1

mrc1Enabled OBJECT-TYPE
	SYNTAX		DisplayString
	MAX-ACCESS	read-only
	STATUS 		current
	DESCRIPTION	
	 "MRC 1 is Enabled?"
	::= { mrc1 1 }    -- 1.3.6.1.4.1.2366.6.1.2.1.3.1.1

mrc1Master OBJECT-TYPE
	SYNTAX		DisplayString
	MAX-ACCESS	read-only
	STATUS 		current
	DESCRIPTION	
	 "MRC 1 is Master?"
	::= { mrc1 2 }    -- 1.3.6.1.4.1.2366.6.1.2.1.3.1.2

mrc1Position OBJECT-TYPE
	SYNTAX		Integer32
	MAX-ACCESS	read-only
	STATUS 		current
	DESCRIPTION	
	 "MRC 1 Position - value 0 or 1.  -1 = Unknown"
	::= { mrc1 3 }    -- 1.3.6.1.4.1.2366.6.1.2.1.3.1.3


mrc1Status OBJECT-TYPE
	SYNTAX		Integer32
	MAX-ACCESS	read-only
	STATUS 		current
	DESCRIPTION	
	 "MRC 1 current Status"
	::= { mrc1 4 }    -- 1.3.6.1.4.1.2366.6.1.2.1.3.1.4


mrc1StatusDetails OBJECT-TYPE
	SYNTAX		Integer32
	MAX-ACCESS	read-only
	STATUS 		current
	DESCRIPTION	
	 "MRC 1 Status Details"
	::= { mrc1 5 }    -- 1.3.6.1.4.1.2366.6.1.2.1.3.1.5
	
mrc1PartNum OBJECT-TYPE
	SYNTAX		DisplayString
	MAX-ACCESS	read-only
	STATUS 		current
	DESCRIPTION	
	 "MRC 1 Part Number"
	::= { mrc1 6 }    -- 1.3.6.1.4.1.2366.6.1.2.1.3.1.6

mrc1SerialNum OBJECT-TYPE
	SYNTAX		DisplayString
	MAX-ACCESS	read-only
	STATUS 		current
	DESCRIPTION	
	 "MRC 1 Serial Number"
	::= { mrc1 7 }    -- 1.3.6.1.4.1.2366.6.1.2.1.3.1.7

mrc1FirmwareVersion OBJECT-TYPE
	SYNTAX		DisplayString
	MAX-ACCESS	read-only
	STATUS 		current
	DESCRIPTION	
	 "MRC 1 Firmware Version"
	::= { mrc1 8 }    -- 1.3.6.1.4.1.2366.6.1.2.1.3.1.8

mrc1HardwareVersion OBJECT-TYPE
	SYNTAX		DisplayString
	MAX-ACCESS	read-only
	STATUS 		current
	DESCRIPTION	
	 "MRC 1 HardwareVersion Version"
	::= { mrc1 9 }    -- 1.3.6.1.4.1.2366.6.1.2.1.3.1.9

mrc1Temperature OBJECT-TYPE
	SYNTAX		Integer32
	MAX-ACCESS	read-only
	STATUS 		current
	DESCRIPTION	
	 "MRC 1 current temperature - degrees F"
	::= { mrc1 10 }    -- 1.3.6.1.4.1.2366.6.1.2.1.3.1.10

mrc1TempThreshWarn OBJECT-TYPE
	SYNTAX		Integer32
	MAX-ACCESS	read-only
	STATUS 		current
	DESCRIPTION	
	 "MRC 1 Warning Temperature Threshold - degrees F"
	::= { mrc1 11 }    -- 1.3.6.1.4.1.2366.6.1.2.1.3.1.11

mrc1TempThreshCrit OBJECT-TYPE
	SYNTAX		Integer32
	MAX-ACCESS	read-only
	STATUS 		current
	DESCRIPTION	
	 "MRC 1 Critical Temperature Threshold - degrees F"
	::= { mrc1 12 }    -- 1.3.6.1.4.1.2366.6.1.2.1.3.1.12
	
mrc1FcStatus OBJECT-TYPE
	SYNTAX		Integer32
	MAX-ACCESS	read-only
	STATUS 		current
	DESCRIPTION	
	 "MRC 1 Fibre Channel Status"
	::= { mrc1 13 }    -- 1.3.6.1.4.1.2366.6.1.2.1.3.1.13

mrc1FcType OBJECT-TYPE
	SYNTAX		Integer32
	MAX-ACCESS	read-only
	STATUS 		current
	DESCRIPTION	
	 "MRC 1 Fibre Channel Type"
	::= { mrc1 14 }    -- 1.3.6.1.4.1.2366.6.1.2.1.3.1.14
	
mrc1FcPortWWN OBJECT-TYPE
	SYNTAX		DisplayString
	MAX-ACCESS	read-only
	STATUS 		current
	DESCRIPTION	
	 "MRC 1 Fibre Channel Port WWN"
	::= { mrc1 15 }    -- 1.3.6.1.4.1.2366.6.1.2.1.3.1.15	
		
mrc1FcSpeed OBJECT-TYPE
	SYNTAX		Integer32
	MAX-ACCESS	read-only
	STATUS 		current
	DESCRIPTION	
	 "MRC 1 Fibre Channel Speed"
	::= { mrc1 16 }    -- 1.3.6.1.4.1.2366.6.1.2.1.3.1.16
		
 mrc1StatusStr OBJECT-TYPE
	SYNTAX		DisplayString
	MAX-ACCESS	read-only
	STATUS 		current
	DESCRIPTION	
	 "MRC 1 Status String"
	::= { mrc1 17 }    -- 1.3.6.1.4.1.2366.6.1.2.1.3.1.17	
	
mrc1StatusDetailsStr OBJECT-TYPE
	SYNTAX		DisplayString
	MAX-ACCESS	read-only
	STATUS 		current
	DESCRIPTION	
	 "MRC 1 Status Details String"
	::= { mrc1 18 }    -- 1.3.6.1.4.1.2366.6.1.2.1.3.1.18	
	
mrc1FcPortStatusStr OBJECT-TYPE
	SYNTAX		DisplayString
	MAX-ACCESS	read-only
	STATUS 		current
	DESCRIPTION	
	 "MRC 1 Fibre Channel Port Status String"
	::= { mrc1 19 }    -- 1.3.6.1.4.1.2366.6.1.2.1.3.1.19
	
mrc1WWN OBJECT-TYPE
	SYNTAX		DisplayString
	MAX-ACCESS	read-only
	STATUS 		current
	DESCRIPTION	
	 "MRC 1 WWN"
	::= { mrc1 20 }    -- 1.3.6.1.4.1.2366.6.1.2.1.3.1.20
	
mrc1FcPortTypeStr OBJECT-TYPE
	SYNTAX		DisplayString
	MAX-ACCESS	read-only
	STATUS 		current
	DESCRIPTION	
	 "MRC 1 Fibre Channel Port Type String"
	::= { mrc1 21 }    -- 1.3.6.1.4.1.2366.6.1.2.1.3.1.21	
	
mrc1SfpIsPresent OBJECT-TYPE
	SYNTAX		DisplayString
	MAX-ACCESS	read-only
	STATUS 		current
	DESCRIPTION	
	 "SFP 1 is present?"
	::= { mrc1 22 }    -- 1.3.6.1.4.1.2366.6.1.2.1.3.1.22	
	
mrc1SfpStatus OBJECT-TYPE
	SYNTAX		Integer32
	MAX-ACCESS	read-only
	STATUS 		current
	DESCRIPTION	
	 "SFP 1 current Status"
	::= { mrc1 23 }    -- 1.3.6.1.4.1.2366.6.1.2.1.3.1.23
	
 mrc1FspStatusStr OBJECT-TYPE
	SYNTAX		DisplayString
	MAX-ACCESS	read-only
	STATUS 		current
	DESCRIPTION	
	 "SFP 1 Status String"
	::= { mrc1 24 }    -- 1.3.6.1.4.1.2366.6.1.2.1.3.1.24	
			
mrc1SfpHardwareVersion OBJECT-TYPE
	SYNTAX		DisplayString
	MAX-ACCESS	read-only
	STATUS 		current
	DESCRIPTION	
	 "SFP 1 HardwareVersion Version"
	::= { mrc1 25 }    -- 1.3.6.1.4.1.2366.6.1.2.1.3.1.25
				
mrc1SfpSerialNum OBJECT-TYPE
	SYNTAX		DisplayString
	MAX-ACCESS	read-only
	STATUS 		current
	DESCRIPTION	
	 "SFP 1 Serial Number"
	::= { mrc1 26 }    -- 1.3.6.1.4.1.2366.6.1.2.1.3.1.26
					
mrc1SfpPartNum OBJECT-TYPE
	SYNTAX		DisplayString
	MAX-ACCESS	read-only
	STATUS 		current
	DESCRIPTION	
	 "SFP 1 Part Number"
	::= { mrc1 27 }    -- 1.3.6.1.4.1.2366.6.1.2.1.3.1.27
						
-- ********************************** MRC 2 **********************************

mrc2 OBJECT IDENTIFIER    ::= { iseMrcs 2 } -- 1.3.6.1.4.1.2366.6.1.2.1.3.2

mrc2Enabled OBJECT-TYPE
	SYNTAX		DisplayString
	MAX-ACCESS	read-only
	STATUS 		current
	DESCRIPTION	
	 "MRC 2 is Enabled?"
	::= { mrc2 1 }    -- 1.3.6.1.4.1.2366.6.1.2.1.3.2.1

mrc2Master OBJECT-TYPE
	SYNTAX		DisplayString
	MAX-ACCESS	read-only
	STATUS 		current
	DESCRIPTION	
	 "MRC 2 is Master?"
	::= { mrc2 2 }    -- 1.3.6.1.4.1.2366.6.1.2.1.3.2.2

mrc2Position OBJECT-TYPE
	SYNTAX		Integer32
	MAX-ACCESS	read-only
	STATUS 		current
	DESCRIPTION	
	 "MRC 2 Position - value 0 or 1.  -1 = Unknown"
	::= { mrc2 3 }    -- 1.3.6.1.4.1.2366.6.1.2.1.3.2.3


mrc2Status OBJECT-TYPE
	SYNTAX		Integer32
	MAX-ACCESS	read-only
	STATUS 		current
	DESCRIPTION	
	 "MRC 2 current Status"
	::= { mrc2 4 }    -- 1.3.6.1.4.1.2366.6.1.2.1.3.2.4


mrc2StatusDetails OBJECT-TYPE
	SYNTAX		Integer32
	MAX-ACCESS	read-only
	STATUS 		current
	DESCRIPTION	
	 "MRC 2 Status Details"
	::= { mrc2 5 }    -- 1.3.6.1.4.1.2366.6.1.2.1.3.2.5
	
mrc2PartNum OBJECT-TYPE
	SYNTAX		DisplayString
	MAX-ACCESS	read-only
	STATUS 		current
	DESCRIPTION	
	 "MRC 2 Part Number"
	::= { mrc2 6 }    -- 1.3.6.1.4.1.2366.6.1.2.1.3.2.6

mrc2SerialNum OBJECT-TYPE
	SYNTAX		DisplayString
	MAX-ACCESS	read-only
	STATUS 		current
	DESCRIPTION	
	 "MRC 2 Serial Number"
	::= { mrc2 7 }    -- 1.3.6.1.4.1.2366.6.1.2.1.3.2.7

mrc2FirmwareVersion OBJECT-TYPE
	SYNTAX		DisplayString
	MAX-ACCESS	read-only
	STATUS 		current
	DESCRIPTION	
	 "MRC 2 Firmware Version"
	::= { mrc2 8 }    -- 1.3.6.1.4.1.2366.6.1.2.1.3.2.8

mrc2HardwareVersion OBJECT-TYPE
	SYNTAX		DisplayString
	MAX-ACCESS	read-only
	STATUS 		current
	DESCRIPTION	
	 "MRC 2 HardwareVersion Version"
	::= { mrc2 9 }    -- 1.3.6.1.4.1.2366.6.1.2.1.3.2.9
		
mrc2Temperature OBJECT-TYPE
	SYNTAX		Integer32
	MAX-ACCESS	read-only
	STATUS 		current
	DESCRIPTION	
	 "MRC 2 current temperature - degrees F"
	::= { mrc2 10 }    -- 1.3.6.1.4.1.2366.6.1.2.1.3.2.10

mrc2TempThreshWarn OBJECT-TYPE
	SYNTAX		Integer32
	MAX-ACCESS	read-only
	STATUS 		current
	DESCRIPTION	
	 "MRC 2 Warning Temperature Threshold - degrees F"
	::= { mrc2 11 }    -- 1.3.6.1.4.1.2366.6.1.2.1.3.2.11

mrc2TempThreshCrit OBJECT-TYPE
	SYNTAX		Integer32
	MAX-ACCESS	read-only
	STATUS 		current
	DESCRIPTION	
	 "MRC 2 Critical Temperature Threshold - degrees F"
	::= { mrc2 12 }    -- 1.3.6.1.4.1.2366.6.1.2.1.3.2.12
	
mrc2FcStatus OBJECT-TYPE
	SYNTAX		Integer32
	MAX-ACCESS	read-only
	STATUS 		current
	DESCRIPTION	
	 "MRC 2 Fibre Channel Status"
	::= { mrc2 13 }    -- 1.3.6.1.4.1.2366.6.1.2.1.3.2.13

mrc2FcType OBJECT-TYPE
	SYNTAX		Integer32
	MAX-ACCESS	read-only
	STATUS 		current
	DESCRIPTION	
	 "MRC 2 Fibre Channel Type"
	::= { mrc2 14 }    -- 1.3.6.1.4.1.2366.6.1.2.1.3.2.14
	
mrc2FcPortWWN OBJECT-TYPE
	SYNTAX		DisplayString
	MAX-ACCESS	read-only
	STATUS 		current
	DESCRIPTION	
	 "MRC 2 Fibre Channel Port WWN"
	::= { mrc2 15 }    -- 1.3.6.1.4.1.2366.6.1.2.1.3.2.15	
		
mrc2FcSpeed OBJECT-TYPE
	SYNTAX		Integer32
	MAX-ACCESS	read-only
	STATUS 		current
	DESCRIPTION	
	 "MRC 2 Fibre Channel Speed"
	::= { mrc2 16 }    -- 1.3.6.1.4.1.2366.6.1.2.1.3.2.16
	
 mrc2StatusStr OBJECT-TYPE
	SYNTAX		DisplayString
	MAX-ACCESS	read-only
	STATUS 		current
	DESCRIPTION	
	 "MRC 2 Status String"
	::= { mrc2 17 }    -- 1.3.6.1.4.1.2366.6.1.2.1.3.2.17	
	
mrc2StatusDetailsStr OBJECT-TYPE
	SYNTAX		DisplayString
	MAX-ACCESS	read-only
	STATUS 		current
	DESCRIPTION	
	 "MRC 2 Status Details String"
	::= { mrc2 18 }    -- 1.3.6.1.4.1.2366.6.1.2.1.3.2.18	
	
mrc2FcPortStatusStr OBJECT-TYPE
	SYNTAX		DisplayString
	MAX-ACCESS	read-only
	STATUS 		current
	DESCRIPTION	
	 "MRC 2 Fibre Channel Port Status String"
	::= { mrc2 19 }    -- 1.3.6.1.4.1.2366.6.1.2.1.3.2.19
	
mrc2WWN OBJECT-TYPE
	SYNTAX		DisplayString
	MAX-ACCESS	read-only
	STATUS 		current
	DESCRIPTION	
	 "MRC 2 WWN"
	::= { mrc2 20 }    -- 1.3.6.1.4.1.2366.6.1.2.1.3.2.20
	
mrc2FcPortTypeStr OBJECT-TYPE
	SYNTAX		DisplayString
	MAX-ACCESS	read-only
	STATUS 		current
	DESCRIPTION	
	 "MRC 2 Fibre Channel Port Type String"
	::= { mrc2 21 }    -- 1.3.6.1.4.1.2366.6.1.2.1.3.2.21	
	
mrc2SfpIsPresent OBJECT-TYPE
	SYNTAX		DisplayString
	MAX-ACCESS	read-only
	STATUS 		current
	DESCRIPTION	
	 "SFP 2 is present?"
	::= { mrc2 22 }    -- 1.3.6.1.4.1.2366.6.1.2.1.3.2.22	
	
mrc2SfpStatus OBJECT-TYPE
	SYNTAX		Integer32
	MAX-ACCESS	read-only
	STATUS 		current
	DESCRIPTION	
	 "SFP 2 current Status"
	::= { mrc2 23 }    -- 1.3.6.1.4.1.2366.6.1.2.1.3.2.23
	
 mrc2FspStatusStr OBJECT-TYPE
	SYNTAX		DisplayString
	MAX-ACCESS	read-only
	STATUS 		current
	DESCRIPTION	
	 "SFP 2 Status String"
	::= { mrc2 24 }    -- 1.3.6.1.4.1.2366.6.1.2.1.3.2.24	
			
mrc2SfpHardwareVersion OBJECT-TYPE
	SYNTAX		DisplayString
	MAX-ACCESS	read-only
	STATUS 		current
	DESCRIPTION	
	 "SFP 2 HardwareVersion Version"
	::= { mrc2 25 }    -- 1.3.6.1.4.1.2366.6.1.2.1.3.2.25
				
mrc2SfpSerialNum OBJECT-TYPE
	SYNTAX		DisplayString
	MAX-ACCESS	read-only
	STATUS 		current
	DESCRIPTION	
	 "SFP 2 Serial Number"
	::= { mrc2 26 }    -- 1.3.6.1.4.1.2366.6.1.2.1.3.2.26
					
mrc2SfpPartNum OBJECT-TYPE
	SYNTAX		DisplayString
	MAX-ACCESS	read-only
	STATUS 		current
	DESCRIPTION	
	 "SFP 2 Part Number"
	::= { mrc2 27 }    -- 1.3.6.1.4.1.2366.6.1.2.1.3.2.27	
			
-- ************************** dataPac1 *******************************

-- iseDataPacs  OBJECT IDENTIFIER	::= { iseObjects 4 }  - 1.3.6.1.4.1.2366.6.1.2.1.4

dataPac1 OBJECT IDENTIFIER       ::= { iseDataPacs 1 }     -- 1.3.6.1.4.1.2366.6.1.2.1.4.1

dataPac1PartNum OBJECT-TYPE
	SYNTAX		DisplayString
	MAX-ACCESS 	read-only
	STATUS 		current
	DESCRIPTION	
	 "DataPac 1 Part Number"
	::= { dataPac1 1 }    -- 1.3.6.1.4.1.2366.6.1.2.1.4.1.1
	
dataPac1Type OBJECT-TYPE
	SYNTAX		DisplayString
	MAX-ACCESS 	read-only
	STATUS 		current
	DESCRIPTION	
	 "DataPac 1 Type"
	::= { dataPac1 2 }    -- 1.3.6.1.4.1.2366.6.1.2.1.4.1.2

dataPac1Status OBJECT-TYPE
	SYNTAX		Integer32
	MAX-ACCESS 	read-only
	STATUS 		current
	DESCRIPTION	
	 "DataPac 1 Status"
	::= { dataPac1 3 }    -- 1.3.6.1.4.1.2366.6.1.2.1.4.1.3

dataPac1StatusDetails OBJECT-TYPE
	SYNTAX		Integer32
	MAX-ACCESS 	read-only
	STATUS 		current
	DESCRIPTION	
	 "DataPac 1 Status Details"
	::= { dataPac1 4 }    -- 1.3.6.1.4.1.2366.6.1.2.1.4.1.4
	
dataPac1SerialNum OBJECT-TYPE
	SYNTAX		DisplayString
	MAX-ACCESS 	read-only
	STATUS 		current
	DESCRIPTION	
	 "DataPac 1 Serial Number"
	::= { dataPac1 5 }    -- 1.3.6.1.4.1.2366.6.1.2.1.4.1.5

dataPac1FwVersion OBJECT-TYPE
	SYNTAX		DisplayString
	MAX-ACCESS 	read-only
	STATUS 		current
	DESCRIPTION	
	 "DataPac 1 Firmware Version"
	::= { dataPac1 6 }    -- 1.3.6.1.4.1.2366.6.1.2.1.4.1.6

dataPac1Capacity OBJECT-TYPE
	SYNTAX		Integer32
	MAX-ACCESS 	read-only
	STATUS 		current
	DESCRIPTION	
	 "DataPac 1 capacity in GB"
	::= { dataPac1 8 }    -- 1.3.6.1.4.1.2366.6.1.2.1.4.1.8

dataPac1SpareLevel OBJECT-TYPE
	SYNTAX		Integer32
	MAX-ACCESS 	read-only
	STATUS 		current
	DESCRIPTION	
	 "DataPac 1 Spare Level"
	::= { dataPac1 9 }    -- 1.3.6.1.4.1.2366.6.1.2.1.4.1.9

dataPac1Temperature OBJECT-TYPE
	SYNTAX		Integer32
	MAX-ACCESS 	read-only
	STATUS 		current
	DESCRIPTION	
	 "DataPac 1 current temperature - degrees F"
	::= { dataPac1 10 }    -- 1.3.6.1.4.1.2366.6.1.2.1.4.1.10

dataPac1TempThreshWarn OBJECT-TYPE
	SYNTAX		Integer32
	MAX-ACCESS 	read-only
	STATUS 		current
	DESCRIPTION	
	 "DataPac 1 Warning Temperature Threshold - degrees"
	::= { dataPac1 11 }    -- 1.3.6.1.4.1.2366.6.1.2.1.4.1.11

dataPac1TempThreshCrit OBJECT-TYPE
	SYNTAX		Integer32
	MAX-ACCESS 	read-only
	STATUS 		current
	DESCRIPTION	
	 "DataPac 1 Critical Temperature Threshold - degrees"
	::= { dataPac1 12 }    -- 1.3.6.1.4.1.2366.6.1.2.1.4.1.12

 dataPac1Health OBJECT-TYPE
	SYNTAX		Integer32
	MAX-ACCESS 	read-only
	STATUS 		current
	DESCRIPTION	
	 "DataPac 1 Current Health"
	::= { dataPac1 13 }    -- 1.3.6.1.4.1.2366.6.1.2.1.4.1.13
	
dataPac1NumDrives OBJECT-TYPE
	SYNTAX		Integer32
	MAX-ACCESS 	read-only
	STATUS 		current
	DESCRIPTION	
	 "DataPac 1 Number of Drives"
	::= { dataPac1 14 }    -- 1.3.6.1.4.1.2366.6.1.2.1.4.1.14
	
dataPac1NumBadDrives OBJECT-TYPE
	SYNTAX		Integer32
	MAX-ACCESS 	read-only
	STATUS 		current
	DESCRIPTION	
	 "DataPac 1 Number of Bad Drives"
	::= { dataPac1 15 }    -- 1.3.6.1.4.1.2366.6.1.2.1.4.1.15

dataPac1StatusStr OBJECT-TYPE
	SYNTAX		DisplayString
	MAX-ACCESS 	read-only
	STATUS 		current
	DESCRIPTION	
	 "DataPac 1 Status String"
	::= { dataPac1 16 }    -- 1.3.6.1.4.1.2366.6.1.2.1.4.1.16	
	
dataPac1StatusDetailsStr OBJECT-TYPE
	SYNTAX		DisplayString
	MAX-ACCESS 	read-only
	STATUS 		current
	DESCRIPTION	
	 "DataPac 1 Status Details String"
	::= { dataPac1 17 }    -- 1.3.6.1.4.1.2366.6.1.2.1.4.1.17
	
dataPac1Position OBJECT-TYPE
	SYNTAX		Integer32
	MAX-ACCESS 	read-only
	STATUS 		current
	DESCRIPTION	
	 "DataPac 1 Position"
	::= { dataPac1 18 }    -- 1.3.6.1.4.1.2366.6.1.2.1.4.1.18

-- ************************** dataPac2 *******************************

dataPac2 OBJECT IDENTIFIER       ::= { iseDataPacs 2 }     -- 1.3.6.1.4.1.2366.6.1.2.1.4.2


dataPac2PartNum OBJECT-TYPE
	SYNTAX		DisplayString
	MAX-ACCESS 	read-only
	STATUS 		current
	DESCRIPTION	
	 "DataPac 2 Part Number"
	::= { dataPac2 1 }    -- 1.3.6.1.4.1.2366.6.1.2.1.4.1.1
	
dataPac2Type OBJECT-TYPE
	SYNTAX		DisplayString
	MAX-ACCESS 	read-only
	STATUS 		current
	DESCRIPTION	
	 "DataPac 2 Type"
	::= { dataPac2 2 }    -- 1.3.6.1.4.1.2366.6.1.2.1.4.1.2

dataPac2Status OBJECT-TYPE
	SYNTAX		Integer32
	MAX-ACCESS 	read-only
	STATUS 		current
	DESCRIPTION	
	 "DataPac 2 Status"
	::= { dataPac2 3 }    -- 1.3.6.1.4.1.2366.6.1.2.1.4.1.3

dataPac2StatusDetails OBJECT-TYPE
	SYNTAX		Integer32
	MAX-ACCESS 	read-only
	STATUS 		current
	DESCRIPTION	
	 "DataPac 2 Status Details"
	::= { dataPac2 4 }    -- 1.3.6.1.4.1.2366.6.1.2.1.4.1.4
	
dataPac2SerialNum OBJECT-TYPE
	SYNTAX		DisplayString
	MAX-ACCESS 	read-only
	STATUS 		current
	DESCRIPTION	
	 "DataPac 2 Serial Number"
	::= { dataPac2 5 }    -- 1.3.6.1.4.1.2366.6.1.2.1.4.1.5

dataPac2FwVersion OBJECT-TYPE
	SYNTAX		DisplayString
	MAX-ACCESS 	read-only
	STATUS 		current
	DESCRIPTION	
	 "DataPac 2 Firmware Version"
	::= { dataPac2 6 }    -- 1.3.6.1.4.1.2366.6.1.2.1.4.1.6

dataPac2Capacity OBJECT-TYPE
	SYNTAX		Integer32
	MAX-ACCESS 	read-only
	STATUS 		current
	DESCRIPTION	
	 "DataPac 2 capacity in GB"
	::= { dataPac2 8 }    -- 1.3.6.1.4.1.2366.6.1.2.1.4.1.8

dataPac2SpareLevel OBJECT-TYPE
	SYNTAX		Integer32
	MAX-ACCESS 	read-only
	STATUS 		current
	DESCRIPTION	
	 "DataPac 2 Spare Level"
	::= { dataPac2 9 }    -- 1.3.6.1.4.1.2366.6.1.2.1.4.1.9

dataPac2Temperature OBJECT-TYPE
	SYNTAX		Integer32
	MAX-ACCESS 	read-only
	STATUS 		current
	DESCRIPTION	
	 "DataPac 2 current temperature - degrees F"
	::= { dataPac2 10 }    -- 1.3.6.1.4.1.2366.6.1.2.1.4.1.10

dataPac2TempThreshWarn OBJECT-TYPE
	SYNTAX		Integer32
	MAX-ACCESS 	read-only
	STATUS 		current
	DESCRIPTION	
	 "DataPac 2 Warning Temperature Threshold - degrees"
	::= { dataPac2 11 }    -- 1.3.6.1.4.1.2366.6.1.2.1.4.1.11

dataPac2TempThreshCrit OBJECT-TYPE
	SYNTAX		Integer32
	MAX-ACCESS 	read-only
	STATUS 		current
	DESCRIPTION	
	 "DataPac 2 Critical Temperature Threshold - degrees"
	::= { dataPac2 12 }    -- 1.3.6.1.4.1.2366.6.1.2.1.4.1.12

 dataPac2Health OBJECT-TYPE
	SYNTAX		Integer32
	MAX-ACCESS 	read-only
	STATUS 		current
	DESCRIPTION	
	 "DataPac 2 Current Health"
	::= { dataPac2 13 }    -- 1.3.6.1.4.1.2366.6.1.2.1.4.1.13
	
dataPac2NumDrives OBJECT-TYPE
	SYNTAX		Integer32
	MAX-ACCESS 	read-only
	STATUS 		current
	DESCRIPTION	
	 "DataPac 2 Number of Drives"
	::= { dataPac2 14 }    -- 1.3.6.1.4.1.2366.6.1.2.1.4.1.14
	
dataPac2NumBadDrives OBJECT-TYPE
	SYNTAX		Integer32
	MAX-ACCESS 	read-only
	STATUS 		current
	DESCRIPTION	
	 "DataPac 2 Number of Bad Drives"
	::= { dataPac2 15 }    -- 1.3.6.1.4.1.2366.6.1.2.1.4.1.15

dataPac2StatusStr OBJECT-TYPE
	SYNTAX		DisplayString
	MAX-ACCESS 	read-only
	STATUS 		current
	DESCRIPTION	
	 "DataPac 2 Status String"
	::= { dataPac2 16 }    -- 1.3.6.1.4.1.2366.6.1.2.1.4.2.16	
	
dataPac2StatusDetailsStr OBJECT-TYPE
	SYNTAX		DisplayString
	MAX-ACCESS 	read-only
	STATUS 		current
	DESCRIPTION	
	 "DataPac 2 Status Details String"
	::= { dataPac2 17 }    -- 1.3.6.1.4.1.2366.6.1.2.1.4.2.17
	
dataPac2Position OBJECT-TYPE
	SYNTAX		Integer32
	MAX-ACCESS 	read-only
	STATUS 		current
	DESCRIPTION	
	 "DataPac 2 Position"
	::= { dataPac2 18 }    -- 1.3.6.1.4.1.2366.6.1.2.1.4.2.18	
	
-- ******************************* asaStoragePool1 ********************************
-- iseStoragePools  OBJECT IDENTIFIER  ::= { iseObjects 5 }  - 1.3.6.1.4.1.2366.6.1.2.1.5 

storagePool1 OBJECT IDENTIFIER ::= { iseStoragePools 1 }  -- 1.3.6.1.4.1.2366.6.1.2.1.5.1

storagePool1Id  OBJECT-TYPE
	SYNTAX		DisplayString
	MAX-ACCESS 	read-only
	STATUS 		current
	DESCRIPTION	
	 "Storage Pool 1 ID"
	::= { storagePool1 1 }    -- 1.3.6.1.4.1.2366.6.1.2.1.5.1.1

storagePool1DataPacUsage OBJECT-TYPE
	SYNTAX		Integer32
	MAX-ACCESS 	read-only
	STATUS 		current
	DESCRIPTION	
	 "Storage Pool 1 DataPac usage ( 0 = Unknown, 1 = DataPac1, 2 = DataPac2, 3 = both DataPacs ) "
	::= { storagePool1 2 }    -- 1.3.6.1.4.1.2366.6.1.2.1.5.1.2

storagePool1Status OBJECT-TYPE
	SYNTAX		Integer32
	MAX-ACCESS 	read-only
	STATUS 		current
	DESCRIPTION	
	 "Storage Pool 1 Status"
	::= { storagePool1 3 }    -- 1.3.6.1.4.1.2366.6.1.2.1.5.1.3

storagePool1TotalAvailableSpace OBJECT-TYPE
	SYNTAX		Integer32
	MAX-ACCESS 	read-only
	STATUS 		current
	DESCRIPTION	
	 "Storage Pool 1 Total Available Space"
	::= { storagePool1 4 }    -- 1.3.6.1.4.1.2366.6.1.2.1.5.1.4

storagePool1TotalManagedSpace OBJECT-TYPE
	SYNTAX		Integer32
	MAX-ACCESS 	read-only
	STATUS 		current
	DESCRIPTION	
	 "Storage Pool 1 Total Managed Space"
	::= { storagePool1 5 }    -- 1.3.6.1.4.1.2366.6.1.2.1.5.1.5

storagePool1MaxSizeRaid0 OBJECT-TYPE
	SYNTAX		Integer32
	MAX-ACCESS 	read-only
	STATUS 		current
	DESCRIPTION	
	 "Storage Pool 1 Max Raid 0 Size"
	::= { storagePool1 6 }    -- 1.3.6.1.4.1.2366.6.1.2.1.5.1.6

storagePool1MaxSizeRaid1 OBJECT-TYPE
	SYNTAX		Integer32
	MAX-ACCESS 	read-only
	STATUS 		current
	DESCRIPTION	
	 "Storage Pool 1 Max Raid 1 Size"
	::= { storagePool1 7 }    -- 1.3.6.1.4.1.2366.6.1.2.1.5.1.7
	
storagePool1MaxSizeRaid5 OBJECT-TYPE
	SYNTAX		Integer32
	MAX-ACCESS 	read-only
	STATUS 		current
	DESCRIPTION	
	 "Storage Pool 1 Max Raid 5 Size"
	::= { storagePool1 8 }    -- 1.3.6.1.4.1.2366.2.2.1.5.1.8

storagePool1TotalVolumes OBJECT-TYPE
	SYNTAX		Integer32
	MAX-ACCESS 	read-only
	STATUS 		current
	DESCRIPTION	
	 "Storage Pool 1 - number of created volumes"
	::= { storagePool1 10 }    -- 1.3.6.1.4.1.2366.6.1.2.1.5.1.10
	
storagePool1StatusStr  OBJECT-TYPE
	SYNTAX		DisplayString
	MAX-ACCESS 	read-only
	STATUS 		current
	DESCRIPTION	
	 "Storage Pool 1 Status String"
	::= { storagePool1 11 }    -- 1.3.6.1.4.1.2366.6.1.2.1.5.1.11
	
storagePool1StatusDetails OBJECT-TYPE
	SYNTAX		Integer32
	MAX-ACCESS 	read-only
	STATUS 		current
	DESCRIPTION	
	 "Storage Pool 1 - StatusDetails"
	::= { storagePool1 12 }    -- 1.3.6.1.4.1.2366.6.1.2.1.5.1.12
	
storagePool1StatusDetailsStr  OBJECT-TYPE
	SYNTAX		DisplayString
	MAX-ACCESS 	read-only
	STATUS 		current
	DESCRIPTION	
	 "Storage Pool 1 Status Details String"
	::= { storagePool1 13 }    -- 1.3.6.1.4.1.2366.6.1.2.1.5.1.13
	
storagePool1UUIDStr  OBJECT-TYPE
	SYNTAX		DisplayString
	MAX-ACCESS 	read-only
	STATUS 		current
	DESCRIPTION	
	 "Storage Pool 1 UUID String"
	::= { storagePool1 14 }    -- 1.3.6.1.4.1.2366.6.1.2.1.5.1.14	

-- ******************************* asaStoragePool2 ********************************
-- iseStoragePools  OBJECT IDENTIFIER  ::= { iseObjects 5 }  - 1.3.6.1.4.1.2366.6.1.2.1.5 

storagePool2 OBJECT IDENTIFIER ::= { iseStoragePools 2 }  -- 1.3.6.1.4.1.2366.6.1.2.1.5.2

storagePool2Id  OBJECT-TYPE
	SYNTAX		DisplayString
	MAX-ACCESS 	read-only
	STATUS 		current
	DESCRIPTION	
	 "Storage Pool 2 ID"
	::= { storagePool2 1 }    -- 1.3.6.1.4.1.2366.6.1.2.1.5.2.1

storagePool2DataPacUsage OBJECT-TYPE
	SYNTAX		Integer32
	MAX-ACCESS 	read-only
	STATUS 		current
	DESCRIPTION	
	 "Storage Pool 2 DataPac usage ( 0 = Unknown, 1 = DataPac1, 2 = DataPac2, 3 = both DataPacs ) "
	::= { storagePool2 2 }    -- 1.3.6.1.4.1.2366.6.1.2.1.5.2.2

storagePool2Status OBJECT-TYPE
	SYNTAX		Integer32
	MAX-ACCESS 	read-only
	STATUS 		current
	DESCRIPTION	
	 "Storage Pool 2 Status"
	::= { storagePool2 3 }    -- 1.3.6.1.4.1.2366.6.1.2.1.5.2.3

storagePool2TotalAvailableSpace OBJECT-TYPE
	SYNTAX		Integer32
	MAX-ACCESS 	read-only
	STATUS 		current
	DESCRIPTION	
	 "Storage Pool 2 Total Available Space"
	::= { storagePool2 4 }    -- 1.3.6.1.4.1.2366.6.1.2.1.5.2.4

storagePool2TotalManagedSpace OBJECT-TYPE
	SYNTAX		Integer32
	MAX-ACCESS 	read-only
	STATUS 		current
	DESCRIPTION	
	 "Storage Pool 2 Total Managed Space"
	::= { storagePool2 5 }    -- 1.3.6.1.4.1.2366.6.1.2.1.5.2.5

storagePool2MaxSizeRaid0 OBJECT-TYPE
	SYNTAX		Integer32
	MAX-ACCESS 	read-only
	STATUS 		current
	DESCRIPTION	
	 "Storage Pool 2 Max Raid 0 Size"
	::= { storagePool2 6 }    -- 1.3.6.1.4.1.2366.6.1.2.1.5.2.6

storagePool2MaxSizeRaid1 OBJECT-TYPE
	SYNTAX		Integer32
	MAX-ACCESS 	read-only
	STATUS 		current
	DESCRIPTION	
	 "Storage Pool 2 Max Raid 1 Size"
	::= { storagePool2 7 }    -- 1.3.6.1.4.1.2366.2.2.1.5.2.7 
	
storagePool2MaxSizeRaid5 OBJECT-TYPE
	SYNTAX		Integer32
	MAX-ACCESS 	read-only
	STATUS 		current
	DESCRIPTION	
	 "Storage Pool 2 Max Raid 5 Size"
	::= { storagePool2 8 }    -- 1.3.6.1.4.1.2366.2.2.1.5.2.8

storagePool2TotalVolumes OBJECT-TYPE
	SYNTAX		Integer32
	MAX-ACCESS 	read-only
	STATUS 		current
	DESCRIPTION	
	 "Storage Pool 2 - number of created volumes"
	::= { storagePool2 10 }    -- 1.3.6.1.4.1.2366.6.1.2.1.5.2.10
	
storagePool2StatusStr  OBJECT-TYPE
	SYNTAX		DisplayString
	MAX-ACCESS 	read-only
	STATUS 		current
	DESCRIPTION	
	 "Storage Pool 2 Status String"
	::= { storagePool2 11 }    -- 1.3.6.1.4.1.2366.6.1.2.1.5.2.11
	
storagePool2StatusDetails OBJECT-TYPE
	SYNTAX		Integer32
	MAX-ACCESS 	read-only
	STATUS 		current
	DESCRIPTION	
	 "Storage Pool 2 - StatusDetails"
	::= { storagePool2 12 }    -- 1.3.6.1.4.1.2366.6.1.2.1.5.2.12
	
storagePool2StatusDetailsStr  OBJECT-TYPE
	SYNTAX		DisplayString
	MAX-ACCESS 	read-only
	STATUS 		current
	DESCRIPTION	
	 "Storage Pool 2 Status Details String"
	::= { storagePool2 13 }    -- 1.3.6.1.4.1.2366.6.1.2.1.5.2.13
	
storagePool2UUIDStr  OBJECT-TYPE
	SYNTAX		DisplayString
	MAX-ACCESS 	read-only
	STATUS 		current
	DESCRIPTION	
	 "Storage Pool 2 UUID String"
	::= { storagePool2 14 }    -- 1.3.6.1.4.1.2366.6.1.2.1.5.2.14		

--********************************************************************

-- isePowerSupplies OBJECT IDENTIFIER	::= { iseObjects 6 }   - 1.3.6.1.4.1.2366.6.1.2.1.6

powerSupply1 OBJECT IDENTIFIER ::= { isePowerSupplies 1 }  -- 1.3.6.1.4.1.2366.6.1.2.1.6.1

powerSupply1SerialNum OBJECT-TYPE
	SYNTAX		DisplayString
	MAX-ACCESS 	read-only
	STATUS 		current
	DESCRIPTION	
	 "powerSupply 1 Serial Number"
	::= { powerSupply1 1 }    -- 1.3.6.1.4.1.2366.6.1.2.1.6.1.1

powerSupply1PartNum OBJECT-TYPE
	SYNTAX		DisplayString
	MAX-ACCESS 	read-only
	STATUS 		current
	DESCRIPTION	
	 "powerSupply 1 Part Number"
	::= { powerSupply1 2 }    -- 1.3.6.1.4.1.2366.6.1.2.1.6.1.2

powerSupply1Status OBJECT-TYPE
	SYNTAX		Integer32
	MAX-ACCESS 	read-only
	STATUS 		current
	DESCRIPTION	
	 "Power Supply 1 Current Status"
	::= { powerSupply1 4 }    -- 1.3.6.1.4.1.2366.6.1.2.1.6.1.4
	

powerSupply1StatusDetails OBJECT-TYPE
	SYNTAX		Integer32
	MAX-ACCESS 	read-only
	STATUS 		current
	DESCRIPTION	
	 "Power Supply 1 Status Details"
	::= { powerSupply1 5 }    -- 1.3.6.1.4.1.2366.6.1.2.1.6.1.5	

powerSupply1Temperature OBJECT-TYPE
	SYNTAX		Integer32
	MAX-ACCESS 	read-only
	STATUS 		current
	DESCRIPTION	
	 "Power Supply 1 Current Temperature - degrees C"
	::= { powerSupply1 6 }    -- 1.3.6.1.4.1.2366.6.1.2.1.6.1.6

powerSupply1TempThreshWarn OBJECT-TYPE
	SYNTAX		Integer32
	MAX-ACCESS 	read-only
	STATUS 		current
	DESCRIPTION	
	 "Power Supply 1 Warning Temperature Threshold - degrees C"
	::= { powerSupply1 7 }    -- 1.3.6.1.4.1.2366.6.1.2.1.6.1.7

powerSupply1TempThreshCrit OBJECT-TYPE
	SYNTAX		Integer32
	MAX-ACCESS 	read-only
	STATUS 		current
	DESCRIPTION	
	 "Power Supply 1 Critical Temperature Threshold - degrees C"
	::= { powerSupply1 8 }    -- 1.3.6.1.4.1.2366.6.1.2.1.6.1.8

powerSupply1Position OBJECT-TYPE
	SYNTAX		Integer32
	MAX-ACCESS 	read-only
	STATUS 		current
	DESCRIPTION	
	 "Power Supply 1 Position"
	::= { powerSupply1 9 }    -- 1.3.6.1.4.1.2366.6.1.2.1.6.1.9


powerSupply1FanStatus OBJECT-TYPE
	SYNTAX		Integer32
	MAX-ACCESS 	read-only
	STATUS 		current
	DESCRIPTION	
	 "Power Supply 1 Fan Status"
	::= { powerSupply1 10 }    -- 1.3.6.1.4.1.2366.6.1.2.1.6.1.10

powerSupply1FanSpeed OBJECT-TYPE
	SYNTAX		Integer32
	MAX-ACCESS 	read-only
	STATUS 		current
	DESCRIPTION	
	 "Power Supply 1 Fan 1 Speed"
	::= { powerSupply1 11 }    -- 1.3.6.1.4.1.2366.6.1.2.1.6.1.11


powerSupply1FanDesiredSpeed OBJECT-TYPE
	SYNTAX		Integer32
	MAX-ACCESS 	read-only
	STATUS 		current
	DESCRIPTION	
	 "Power Supply 1 Fan 1 Desired Sdpeed"
	::= { powerSupply1 12 }    -- 1.3.6.1.4.1.2366.6.1.2.1.6.1.12
	
powerSupply1StatusStr OBJECT-TYPE
	SYNTAX		DisplayString
	MAX-ACCESS 	read-only
	STATUS 		current
	DESCRIPTION	
	 "Power Supply 1 Status String"
	::= { powerSupply1 13 }    -- 1.3.6.1.4.1.2366.6.1.2.1.6.1.13
	
powerSupply1StatusDetailsStr OBJECT-TYPE
	SYNTAX		DisplayString
	MAX-ACCESS 	read-only
	STATUS 		current
	DESCRIPTION	
	 "Power Supply 1 Status Details String"
	::= { powerSupply1 14 }    -- 1.3.6.1.4.1.2366.6.1.2.1.6.1.14

powerSupply1FanStatusStr OBJECT-TYPE
	SYNTAX		DisplayString
	MAX-ACCESS 	read-only
	STATUS 		current
	DESCRIPTION	
	 "Power Supply 1 Fan 1 Status String"
	::= { powerSupply1 15 }    -- 1.3.6.1.4.1.2366.6.1.2.1.6.1.15
	
powerSupply1Fan2Status OBJECT-TYPE
	SYNTAX		Integer32
	MAX-ACCESS 	read-only
	STATUS 		current
	DESCRIPTION	
	 "Power Supply 1 Fan 2 Status"
	::= { powerSupply1 16 }    -- 1.3.6.1.4.1.2366.6.1.2.1.6.1.16

powerSupply1Fan2Speed OBJECT-TYPE
	SYNTAX		Integer32
	MAX-ACCESS 	read-only
	STATUS 		current
	DESCRIPTION	
	 "Power Supply 1 Fan 2 Speed"
	::= { powerSupply1 17 }    -- 1.3.6.1.4.1.2366.6.1.2.1.6.1.17


powerSupply1Fan2DesiredSpeed OBJECT-TYPE
	SYNTAX		Integer32
	MAX-ACCESS 	read-only
	STATUS 		current
	DESCRIPTION	
	 "Power Supply 1 Desired Fan 2 Speed"
	::= { powerSupply1 18 }    -- 1.3.6.1.4.1.2366.6.1.2.1.6.1.18	
	
powerSupply1Fan2StatusStr OBJECT-TYPE
	SYNTAX		DisplayString
	MAX-ACCESS 	read-only
	STATUS 		current
	DESCRIPTION	
	 "Power Supply 1 Fan 2 Status String"
	::= { powerSupply1 19 }    -- 1.3.6.1.4.1.2366.6.1.2.1.6.1.19		

--********************************************************************
-- isePowerSupplies OBJECT IDENTIFIER	::= { iseObjects 6 }   - 1.3.6.1.4.1.2366.6.1.2.1.6

powerSupply2 OBJECT IDENTIFIER ::= { isePowerSupplies 2 }  -- 1.3.6.1.4.1.2366.6.1.2.1.6.2

powerSupply2SerialNum OBJECT-TYPE
	SYNTAX		DisplayString
	MAX-ACCESS 	read-only
	STATUS 		current
	DESCRIPTION	
	 "powerSupply 2 Serial Number"
	::= { powerSupply2 1 }    -- 1.3.6.1.4.1.2366.6.1.2.1.6.2.1

powerSupply2PartNum OBJECT-TYPE
	SYNTAX		DisplayString
	MAX-ACCESS 	read-only
	STATUS 		current
	DESCRIPTION	
	 "Power Supply 2 Part Number"
	::= { powerSupply2 2 }    -- 1.3.6.1.4.1.2366.6.1.2.1.6.2.2

powerSupply2Status OBJECT-TYPE
	SYNTAX		Integer32
	MAX-ACCESS 	read-only
	STATUS 		current
	DESCRIPTION	
	 "Power Supply 2 Current Status"
	::= { powerSupply2 4 }    -- 1.3.6.1.4.1.2366.6.1.2.1.6.2.4
	
powerSupply2StatusDetails OBJECT-TYPE
	SYNTAX		Integer32
	MAX-ACCESS 	read-only
	STATUS 		current
	DESCRIPTION	
	 "Power Supply 2 Status Details"
	::= { powerSupply2 5 }    -- 1.3.6.1.4.1.2366.6.1.2.1.6.2.5	

powerSupply2Temperature OBJECT-TYPE
	SYNTAX		Integer32
	MAX-ACCESS 	read-only
	STATUS 		current
	DESCRIPTION	
	 "Power Supply 2 Current Temperature - degrees C"
	::= { powerSupply2 6 }    -- 1.3.6.1.4.1.2366.6.1.2.1.6.2.6

powerSupply2TempThreshWarn OBJECT-TYPE
	SYNTAX		Integer32
	MAX-ACCESS 	read-only
	STATUS 		current
	DESCRIPTION	
	 "Power Supply 2 Warning Temperature Threshold - degrees C"
	::= { powerSupply2 7 }    -- 1.3.6.1.4.1.2366.6.1.2.1.6.2.7

powerSupply2TempThreshCrit OBJECT-TYPE
	SYNTAX		Integer32
	MAX-ACCESS 	read-only
	STATUS 		current
	DESCRIPTION	
	 "Power Supply 2 Critical Temperature Threshold - degrees C"
	::= { powerSupply2 8 }    -- 1.3.6.1.4.1.2366.6.1.2.1.6.2.8

powerSupply2Position OBJECT-TYPE
	SYNTAX		Integer32
	MAX-ACCESS 	read-only
	STATUS 		current
	DESCRIPTION	
	 "Power Supply 2 Position"
	::= { powerSupply2 9 }    -- 1.3.6.1.4.1.2366.6.1.2.1.6.2.9

powerSupply2FanStatus OBJECT-TYPE
	SYNTAX		Integer32
	MAX-ACCESS 	read-only
	STATUS 		current
	DESCRIPTION	
	 "Power Supply 2 Fan Status"
	::= { powerSupply2 10 }    -- 1.3.6.1.4.1.2366.6.1.2.1.6.2.10
	
powerSupply2FanSpeed OBJECT-TYPE
	SYNTAX		Integer32
	MAX-ACCESS 	read-only
	STATUS 		current
	DESCRIPTION	
	 "Power Supply 2 Fan Speed"
	::= { powerSupply2 11 }    -- 1.3.6.1.4.1.2366.6.1.2.1.6.2.11

powerSupply2FanDesiredSpeed OBJECT-TYPE
	SYNTAX		Integer32
	MAX-ACCESS 	read-only
	STATUS 		current
	DESCRIPTION	
	 "Power Supply 2 Desired Fan Speed"
	::= { powerSupply2 12 }    -- 1.3.6.1.4.1.2366.6.1.2.1.6.2.12

powerSupply2StatusStr OBJECT-TYPE
	SYNTAX		DisplayString
	MAX-ACCESS 	read-only
	STATUS 		current
	DESCRIPTION	
	 "powerSupply 2 Status String"
	::= { powerSupply2 13 }    -- 1.3.6.1.4.1.2366.6.1.2.1.6.2.13
	
powerSupply2StatusDetailsStr OBJECT-TYPE
	SYNTAX		DisplayString
	MAX-ACCESS 	read-only
	STATUS 		current
	DESCRIPTION	
	 "powerSupply 2 Status Details String"
	::= { powerSupply2 14 }    -- 1.3.6.1.4.1.2366.6.1.2.1.6.2.14	
	
powerSupply2FanStatusStr OBJECT-TYPE
	SYNTAX		DisplayString
	MAX-ACCESS 	read-only
	STATUS 		current
	DESCRIPTION	
	 "Power Supply 2 Fan 1 Status String"
	::= { powerSupply2 15 }    -- 1.3.6.1.4.1.2366.6.1.2.1.6.2.15
	
powerSupply2Fan2Status OBJECT-TYPE
	SYNTAX		Integer32
	MAX-ACCESS 	read-only
	STATUS 		current
	DESCRIPTION	
	 "Power Supply 2 Fan 2 Status"
	::= { powerSupply2 16 }    -- 1.3.6.1.4.1.2366.6.1.2.1.6.2.16

powerSupply2Fan2Speed OBJECT-TYPE
	SYNTAX		Integer32
	MAX-ACCESS 	read-only
	STATUS 		current
	DESCRIPTION	
	 "Power Supply 2 Fan 2 Speed"
	::= { powerSupply2 17 }    -- 1.3.6.1.4.1.2366.6.1.2.1.6.2.17


powerSupply2Fan2DesiredSpeed OBJECT-TYPE
	SYNTAX		Integer32
	MAX-ACCESS 	read-only
	STATUS 		current
	DESCRIPTION	
	 "Power Supply 2 Desired Fan 2 Speed"
	::= { powerSupply2 18 }    -- 1.3.6.1.4.1.2366.6.1.2.1.6.2.18	
	
powerSupply2Fan2StatusStr OBJECT-TYPE
	SYNTAX		DisplayString
	MAX-ACCESS 	read-only
	STATUS 		current
	DESCRIPTION	
	 "Power Supply 2 Fan 2 Status String"
	::= { powerSupply2 19 }    -- 1.3.6.1.4.1.2366.6.1.2.1.6.2.19	
	
--********************************************************************
-- iseSuperCaps     OBJECT IDENTIFIER	::= { iseObjects 7 }   - 1.3.6.1.4.1.2366.6.1.2.1.7

superCap1 OBJECT IDENTIFIER	::= { iseSuperCaps 1 } -- 1.3.6.1.4.1.2366.6.1.2.1.7.1

superCap1SerialNum OBJECT-TYPE
	SYNTAX		DisplayString
	MAX-ACCESS 	read-only
	STATUS 		current
	DESCRIPTION	
	 "SuperCap 1 Serial Number"
	::= { superCap1 1 }   -- 1.3.6.1.4.1.2366.6.1.2.1.7.1.1

superCap1PartNum OBJECT-TYPE
	SYNTAX		DisplayString
	MAX-ACCESS 	read-only
	STATUS 		current
	DESCRIPTION	
	 "SuperCap 1 Part Number"
	::= { superCap1 2 }   -- 1.3.6.1.4.1.2366.6.1.2.1.7.1.2

superCap1HardwareVersion OBJECT-TYPE
	SYNTAX		DisplayString
	MAX-ACCESS 	read-only
	STATUS 		current
	DESCRIPTION	
	 "SuperCap 1 Hardware Version"
	::= { superCap1 3 }   -- 1.3.6.1.4.1.2366.6.1.2.1.7.1.3

superCap1Status OBJECT-TYPE
	SYNTAX		Integer32
	MAX-ACCESS 	read-only
	STATUS 		current
	DESCRIPTION	
	 "SuperCap 1 Status"
	::= { superCap1 4 }   -- 1.3.6.1.4.1.2366.6.1.2.1.7.1.4
	
superCap1StatusDetails OBJECT-TYPE
	SYNTAX		Integer32
	MAX-ACCESS 	read-only
	STATUS 		current
	DESCRIPTION	
	 "SuperCap 1 Status Details"
	::= { superCap1 5}  -- 1.3.6.1.4.1.2366.6.1.2.1.7.1.5
	
superCap1Temp OBJECT-TYPE
	SYNTAX		Integer32
	MAX-ACCESS 	read-only
	STATUS 		current
	DESCRIPTION	
	 "SuperCap 1 Temperature"
	::= { superCap1 6 }   -- 1.3.6.1.4.1.2366.6.1.2.1.7.1.6	
	
superCap1TempThreshWarn OBJECT-TYPE
	SYNTAX		Integer32
	MAX-ACCESS 	read-only
	STATUS 		current
	DESCRIPTION	
	 "SuperCap 1 Warning Temperature Threshold"
	::= { superCap1 7 }   -- 1.3.6.1.4.1.2366.6.1.2.1.7.1.7		

superCap1TempThreshCrit OBJECT-TYPE
	SYNTAX		Integer32
	MAX-ACCESS 	read-only
	STATUS 		current
	DESCRIPTION	
	 "SuperCap 1 Critical Temperature Threshold"
	::= { superCap1 8 }   -- 1.3.6.1.4.1.2366.6.1.2.1.7.1.8	
		
superCap1Position OBJECT-TYPE
	SYNTAX		Integer32
	MAX-ACCESS 	read-only
	STATUS 		current
	DESCRIPTION	
	 "SuperCap 1 Position"
	::= { superCap1 9 }   -- 1.3.6.1.4.1.2366.6.1.2.1.7.1.9
		
			
	
superCap1StatusStr OBJECT-TYPE
	SYNTAX		DisplayString
	MAX-ACCESS 	read-only
	STATUS 		current
	DESCRIPTION	
	 "SuperCap 1 Status String"
	::= { superCap1 10 }   -- 1.3.6.1.4.1.2366.6.1.2.1.7.1.10
	
superCap1StatusDetailsStr OBJECT-TYPE
	SYNTAX		DisplayString
	MAX-ACCESS 	read-only
	STATUS 		current
	DESCRIPTION	
	 "SuperCap 1 Status Details String"
	::= { superCap1 11 }   -- 1.3.6.1.4.1.2366.6.1.2.1.7.1.11

superCap1Voltage OBJECT-TYPE
	SYNTAX		Integer32
	MAX-ACCESS 	read-only
	STATUS 		current
	DESCRIPTION	
	 "SuperCap 1 Voltage"
	::= { superCap1 12 }   -- 1.3.6.1.4.1.2366.6.1.2.1.7.1.12	
		
--********************************************************************

-- iseSuperCaps     OBJECT IDENTIFIER	::= { iseObjects 8 }   - 1.3.6.1.4.1.2366.6.1.2.1.7
superCap2 OBJECT IDENTIFIER	::= { iseSuperCaps 2 } -- 1.3.6.1.4.1.2366.6.1.2.1.7.2

superCap2SerialNum OBJECT-TYPE
	SYNTAX		DisplayString
	MAX-ACCESS 	read-only
	STATUS 		current
	DESCRIPTION	
	 "SuperCap 2 Serial Number"
	::= { superCap2 1 }  -- 1.3.6.1.4.1.2366.6.1.2.1.7.2.1

superCap2PartNum OBJECT-TYPE
	SYNTAX		DisplayString
	MAX-ACCESS 	read-only
	STATUS 		current
	DESCRIPTION	
	 "SuperCap 2 Part Number"
	::= { superCap2 2 }  -- 1.3.6.1.4.1.2366.6.1.2.1.7.2.2

superCap2HardwareVersion OBJECT-TYPE
	SYNTAX		DisplayString
	MAX-ACCESS 	read-only
	STATUS 		current
	DESCRIPTION	
	 "SuperCap 2 Hardware version"
	::= { superCap2 3 }  -- 1.3.6.1.4.1.2366.6.1.2.1.7.2.3

superCap2Status OBJECT-TYPE
	SYNTAX		Integer32
	MAX-ACCESS 	read-only
	STATUS 		current
	DESCRIPTION	
	 "SuperCap 2 Status"
	::= { superCap2 4 }  -- 1.3.6.1.4.1.2366.6.1.2.1.7.2.4
	
superCap2StatusDetails OBJECT-TYPE
	SYNTAX		Integer32
	MAX-ACCESS 	read-only
	STATUS 		current
	DESCRIPTION	
	 "SuperCap 2 Status Details"
	::= { superCap2 5}  -- 1.3.6.1.4.1.2366.6.1.2.1.7.2.5
	
superCap2Temp OBJECT-TYPE
	SYNTAX		Integer32
	MAX-ACCESS 	read-only
	STATUS 		current
	DESCRIPTION	
	 "SuperCap 2 Temperature"
	::= { superCap2 6 }   -- 1.3.6.1.4.1.2366.6.1.2.1.7.2.6	
	
superCap2TempThreshWarn OBJECT-TYPE
	SYNTAX		Integer32
	MAX-ACCESS 	read-only
	STATUS 		current
	DESCRIPTION	
	 "SuperCap 2 Warning Temperature Threshold"
	::= { superCap2 7 }   -- 1.3.6.1.4.1.2366.6.1.2.1.7.2.7		

superCap2TempThreshCrit OBJECT-TYPE
	SYNTAX		Integer32
	MAX-ACCESS 	read-only
	STATUS 		current
	DESCRIPTION	
	 "SuperCap 2 Critical Temperature Threshold"
	::= { superCap2 8 }   -- 1.3.6.1.4.1.2366.6.1.2.1.7.2.8	
		
superCap2Position OBJECT-TYPE
	SYNTAX		Integer32
	MAX-ACCESS 	read-only
	STATUS 		current
	DESCRIPTION	
	 "SuperCap 2 Position"
	::= { superCap2 9}   -- 1.3.6.1.4.1.2366.6.1.2.1.7.2.9
	
			
superCap2StatusStr OBJECT-TYPE
	SYNTAX		DisplayString
	MAX-ACCESS 	read-only
	STATUS 		current
	DESCRIPTION	
	 "SuperCap 2 Status String"
	::= { superCap2 10 }   -- 1.3.6.1.4.1.2366.6.1.2.1.7.2.10
	
superCap2StatusDetailsStr OBJECT-TYPE
	SYNTAX		DisplayString
	MAX-ACCESS 	read-only
	STATUS 		current
	DESCRIPTION	
	 "SuperCap 2 Status Details String"
	::= { superCap2 11 }   -- 1.3.6.1.4.1.2366.6.1.2.1.7.2.11	
		
superCap2Voltage OBJECT-TYPE
	SYNTAX		Integer32
	MAX-ACCESS 	read-only
	STATUS 		current
	DESCRIPTION	
	 "SuperCap 2 Voltage"
	::= { superCap2 12 }   -- 1.3.6.1.4.1.2366.6.1.2.1.7.2.12
	
--********************************************************************		
	

-- ** VOLUME DEFINITIONS BEGIN
 

 
iseVolume16 OBJECT IDENTIFIER       ::= { iseStorageVols 16 }       -- 1.3.6.1.4.1.2366.6.1.2.1.8.16
 
iseVolume16Name    OBJECT-TYPE
        SYNTAX          DisplayString
        MAX-ACCESS      read-only
        STATUS          current
        DESCRIPTION
        "iseVolume16 Volume Name: ffx_xioB_1"
        ::= { iseVolume16 1 }    -- 1.3.6.1.4.1.2366.6.1.2.1.8.16.1.0
 
iseVolume16VpdId    OBJECT-TYPE
        SYNTAX          DisplayString
        MAX-ACCESS      read-only
        STATUS          current
        DESCRIPTION
        "iseVolume16 Volume VpdId: TBD"
        ::= { iseVolume16 2 }    -- 1.3.6.1.4.1.2366.6.1.2.1.8.16.2.0
 
iseVolume16DetailedStatus    OBJECT-TYPE
        SYNTAX          Integer32
        MAX-ACCESS      read-only
        STATUS          current
        DESCRIPTION
        "iseVolume16 Volume Detailed Status code"
        ::= { iseVolume16 3 }    -- 1.3.6.1.4.1.2366.6.1.2.1.8.16.3.0
 
iseVolume16Status    OBJECT-TYPE
        SYNTAX          Integer32
        MAX-ACCESS      read-only
        STATUS          current
        DESCRIPTION
        "iseVolume16 Volume Status"
        ::= { iseVolume16 4 }    -- 1.3.6.1.4.1.2366.6.1.2.1.8.16.4.0
 
iseVolume16Id    OBJECT-TYPE
        SYNTAX          Integer32
        MAX-ACCESS      read-only
        STATUS          current
        DESCRIPTION
        "iseVolume16 Volume Id"
        ::= { iseVolume16 5 }    -- 1.3.6.1.4.1.2366.6.1.2.1.8.16.5.0
 
iseVolume16RaidType    OBJECT-TYPE
        SYNTAX          Integer32
        MAX-ACCESS      read-only
        STATUS          current
        DESCRIPTION
        "iseVolume16 RaidType"
        ::= { iseVolume16 6 }    -- 1.3.6.1.4.1.2366.6.1.2.1.8.16.6.0
 
iseVolume16Pool    OBJECT-TYPE
        SYNTAX          Integer32
        MAX-ACCESS      read-only
        STATUS          current
        DESCRIPTION
        "iseVolume16 Storage Pool this volume was created from"
        ::= { iseVolume16 7 }    -- 1.3.6.1.4.1.2366.6.1.2.1.8.16.7.0
 
iseVolume16AllocationType    OBJECT-TYPE
        SYNTAX          Integer32
        MAX-ACCESS      read-only
        STATUS          current
        DESCRIPTION
        "iseVolume16 Allocation Type"
        ::= { iseVolume16 8 }    -- 1.3.6.1.4.1.2366.6.1.2.1.8.16.8.0
 
iseVolume16CacheType    OBJECT-TYPE
        SYNTAX          DisplayString
        MAX-ACCESS      read-only
        STATUS          current
        DESCRIPTION
        "iseVolume16 Volume Cache Type"
        ::= { iseVolume16 9 }    -- 1.3.6.1.4.1.2366.6.1.2.1.8.16.9.0
 
iseVolume16Size    OBJECT-TYPE
        SYNTAX          Integer32
        MAX-ACCESS      read-only
        STATUS          current
        DESCRIPTION
        "iseVolume16 Volume Size in GB"
        ::= { iseVolume16 10 }    -- 1.3.6.1.4.1.2366.6.1.2.1.8.16.10.0
 
iseVolume16StatusStr    OBJECT-TYPE
        SYNTAX          DisplayString
        MAX-ACCESS      read-only
        STATUS          current
        DESCRIPTION
        "iseVolume16 Current Status string - short description"
        ::= { iseVolume16 11 }    -- 1.3.6.1.4.1.2366.6.1.2.1.8.16.11.0
 
iseVolume16StatusDetailsStr    OBJECT-TYPE
        SYNTAX          DisplayString
        MAX-ACCESS      read-only
        STATUS          current
        DESCRIPTION
        "iseVolume16 Volume Current Status Details string - longer description when status is not Operational"
        ::= { iseVolume16 12 }    -- 1.3.6.1.4.1.2366.6.1.2.1.8.16.12.0
 
iseVolume16IsSnapshot    OBJECT-TYPE
        SYNTAX          DisplayString
        MAX-ACCESS      read-only
        STATUS          current
        DESCRIPTION
        "iseVolume16 Volume N Is a Snapshot?  value is unknown, yes, or no"
        ::= { iseVolume16 13 }    -- 1.3.6.1.4.1.2366.6.1.2.1.8.16.13.0
 
iseVolume16SnapshotChildId    OBJECT-TYPE
        SYNTAX          Integer32
        MAX-ACCESS      read-only
        STATUS          current
        DESCRIPTION
        "iseVolume16 Volumes Snapshot Child ID - value of 0 means NO Snapshot Child exists"
        ::= { iseVolume16 14 }    -- 1.3.6.1.4.1.2366.6.1.2.1.8.16.14.0
 
iseVolume16SnapshotParentId    OBJECT-TYPE
        SYNTAX          Integer32
        MAX-ACCESS      read-only
        STATUS          current
        DESCRIPTION
        "iseVolume16 Volumes Snapshot Parent ID - value of 0 means NO Snapshot Parent exists"
        ::= { iseVolume16 15 }    -- 1.3.6.1.4.1.2366.6.1.2.1.8.16.15.0
 
iseVolume17 OBJECT IDENTIFIER       ::= { iseStorageVols 17 }       -- 1.3.6.1.4.1.2366.6.1.2.1.8.17
 
iseVolume17Name    OBJECT-TYPE
        SYNTAX          DisplayString
        MAX-ACCESS      read-only
        STATUS          current
        DESCRIPTION
        "iseVolume17 Volume Name: ffx_xioB_2"
        ::= { iseVolume17 1 }    -- 1.3.6.1.4.1.2366.6.1.2.1.8.17.1.0
 
iseVolume17VpdId    OBJECT-TYPE
        SYNTAX          DisplayString
        MAX-ACCESS      read-only
        STATUS          current
        DESCRIPTION
        "iseVolume17 Volume VpdId: TBD"
        ::= { iseVolume17 2 }    -- 1.3.6.1.4.1.2366.6.1.2.1.8.17.2.0
 
iseVolume17DetailedStatus    OBJECT-TYPE
        SYNTAX          Integer32
        MAX-ACCESS      read-only
        STATUS          current
        DESCRIPTION
        "iseVolume17 Volume Detailed Status code"
        ::= { iseVolume17 3 }    -- 1.3.6.1.4.1.2366.6.1.2.1.8.17.3.0
 
iseVolume17Status    OBJECT-TYPE
        SYNTAX          Integer32
        MAX-ACCESS      read-only
        STATUS          current
        DESCRIPTION
        "iseVolume17 Volume Status"
        ::= { iseVolume17 4 }    -- 1.3.6.1.4.1.2366.6.1.2.1.8.17.4.0
 
iseVolume17Id    OBJECT-TYPE
        SYNTAX          Integer32
        MAX-ACCESS      read-only
        STATUS          current
        DESCRIPTION
        "iseVolume17 Volume Id"
        ::= { iseVolume17 5 }    -- 1.3.6.1.4.1.2366.6.1.2.1.8.17.5.0
 
iseVolume17RaidType    OBJECT-TYPE
        SYNTAX          Integer32
        MAX-ACCESS      read-only
        STATUS          current
        DESCRIPTION
        "iseVolume17 RaidType"
        ::= { iseVolume17 6 }    -- 1.3.6.1.4.1.2366.6.1.2.1.8.17.6.0
 
iseVolume17Pool    OBJECT-TYPE
        SYNTAX          Integer32
        MAX-ACCESS      read-only
        STATUS          current
        DESCRIPTION
        "iseVolume17 Storage Pool this volume was created from"
        ::= { iseVolume17 7 }    -- 1.3.6.1.4.1.2366.6.1.2.1.8.17.7.0
 
iseVolume17AllocationType    OBJECT-TYPE
        SYNTAX          Integer32
        MAX-ACCESS      read-only
        STATUS          current
        DESCRIPTION
        "iseVolume17 Allocation Type"
        ::= { iseVolume17 8 }    -- 1.3.6.1.4.1.2366.6.1.2.1.8.17.8.0
 
iseVolume17CacheType    OBJECT-TYPE
        SYNTAX          DisplayString
        MAX-ACCESS      read-only
        STATUS          current
        DESCRIPTION
        "iseVolume17 Volume Cache Type"
        ::= { iseVolume17 9 }    -- 1.3.6.1.4.1.2366.6.1.2.1.8.17.9.0
 
iseVolume17Size    OBJECT-TYPE
        SYNTAX          Integer32
        MAX-ACCESS      read-only
        STATUS          current
        DESCRIPTION
        "iseVolume17 Volume Size in GB"
        ::= { iseVolume17 10 }    -- 1.3.6.1.4.1.2366.6.1.2.1.8.17.10.0
 
iseVolume17StatusStr    OBJECT-TYPE
        SYNTAX          DisplayString
        MAX-ACCESS      read-only
        STATUS          current
        DESCRIPTION
        "iseVolume17 Current Status string - short description"
        ::= { iseVolume17 11 }    -- 1.3.6.1.4.1.2366.6.1.2.1.8.17.11.0
 
iseVolume17StatusDetailsStr    OBJECT-TYPE
        SYNTAX          DisplayString
        MAX-ACCESS      read-only
        STATUS          current
        DESCRIPTION
        "iseVolume17 Volume Current Status Details string - longer description when status is not Operational"
        ::= { iseVolume17 12 }    -- 1.3.6.1.4.1.2366.6.1.2.1.8.17.12.0
 
iseVolume17IsSnapshot    OBJECT-TYPE
        SYNTAX          DisplayString
        MAX-ACCESS      read-only
        STATUS          current
        DESCRIPTION
        "iseVolume17 Volume N Is a Snapshot?  value is unknown, yes, or no"
        ::= { iseVolume17 13 }    -- 1.3.6.1.4.1.2366.6.1.2.1.8.17.13.0
 
iseVolume17SnapshotChildId    OBJECT-TYPE
        SYNTAX          Integer32
        MAX-ACCESS      read-only
        STATUS          current
        DESCRIPTION
        "iseVolume17 Volumes Snapshot Child ID - value of 0 means NO Snapshot Child exists"
        ::= { iseVolume17 14 }    -- 1.3.6.1.4.1.2366.6.1.2.1.8.17.14.0
 
iseVolume17SnapshotParentId    OBJECT-TYPE
        SYNTAX          Integer32
        MAX-ACCESS      read-only
        STATUS          current
        DESCRIPTION
        "iseVolume17 Volumes Snapshot Parent ID - value of 0 means NO Snapshot Parent exists"
        ::= { iseVolume17 15 }    -- 1.3.6.1.4.1.2366.6.1.2.1.8.17.15.0
 
iseVolume18 OBJECT IDENTIFIER       ::= { iseStorageVols 18 }       -- 1.3.6.1.4.1.2366.6.1.2.1.8.18
 
iseVolume18Name    OBJECT-TYPE
        SYNTAX          DisplayString
        MAX-ACCESS      read-only
        STATUS          current
        DESCRIPTION
        "iseVolume18 Volume Name: ffx_xioB_3"
        ::= { iseVolume18 1 }    -- 1.3.6.1.4.1.2366.6.1.2.1.8.18.1.0
 
iseVolume18VpdId    OBJECT-TYPE
        SYNTAX          DisplayString
        MAX-ACCESS      read-only
        STATUS          current
        DESCRIPTION
        "iseVolume18 Volume VpdId: TBD"
        ::= { iseVolume18 2 }    -- 1.3.6.1.4.1.2366.6.1.2.1.8.18.2.0
 
iseVolume18DetailedStatus    OBJECT-TYPE
        SYNTAX          Integer32
        MAX-ACCESS      read-only
        STATUS          current
        DESCRIPTION
        "iseVolume18 Volume Detailed Status code"
        ::= { iseVolume18 3 }    -- 1.3.6.1.4.1.2366.6.1.2.1.8.18.3.0
 
iseVolume18Status    OBJECT-TYPE
        SYNTAX          Integer32
        MAX-ACCESS      read-only
        STATUS          current
        DESCRIPTION
        "iseVolume18 Volume Status"
        ::= { iseVolume18 4 }    -- 1.3.6.1.4.1.2366.6.1.2.1.8.18.4.0
 
iseVolume18Id    OBJECT-TYPE
        SYNTAX          Integer32
        MAX-ACCESS      read-only
        STATUS          current
        DESCRIPTION
        "iseVolume18 Volume Id"
        ::= { iseVolume18 5 }    -- 1.3.6.1.4.1.2366.6.1.2.1.8.18.5.0
 
iseVolume18RaidType    OBJECT-TYPE
        SYNTAX          Integer32
        MAX-ACCESS      read-only
        STATUS          current
        DESCRIPTION
        "iseVolume18 RaidType"
        ::= { iseVolume18 6 }    -- 1.3.6.1.4.1.2366.6.1.2.1.8.18.6.0
 
iseVolume18Pool    OBJECT-TYPE
        SYNTAX          Integer32
        MAX-ACCESS      read-only
        STATUS          current
        DESCRIPTION
        "iseVolume18 Storage Pool this volume was created from"
        ::= { iseVolume18 7 }    -- 1.3.6.1.4.1.2366.6.1.2.1.8.18.7.0
 
iseVolume18AllocationType    OBJECT-TYPE
        SYNTAX          Integer32
        MAX-ACCESS      read-only
        STATUS          current
        DESCRIPTION
        "iseVolume18 Allocation Type"
        ::= { iseVolume18 8 }    -- 1.3.6.1.4.1.2366.6.1.2.1.8.18.8.0
 
iseVolume18CacheType    OBJECT-TYPE
        SYNTAX          DisplayString
        MAX-ACCESS      read-only
        STATUS          current
        DESCRIPTION
        "iseVolume18 Volume Cache Type"
        ::= { iseVolume18 9 }    -- 1.3.6.1.4.1.2366.6.1.2.1.8.18.9.0
 
iseVolume18Size    OBJECT-TYPE
        SYNTAX          Integer32
        MAX-ACCESS      read-only
        STATUS          current
        DESCRIPTION
        "iseVolume18 Volume Size in GB"
        ::= { iseVolume18 10 }    -- 1.3.6.1.4.1.2366.6.1.2.1.8.18.10.0
 
iseVolume18StatusStr    OBJECT-TYPE
        SYNTAX          DisplayString
        MAX-ACCESS      read-only
        STATUS          current
        DESCRIPTION
        "iseVolume18 Current Status string - short description"
        ::= { iseVolume18 11 }    -- 1.3.6.1.4.1.2366.6.1.2.1.8.18.11.0
 
iseVolume18StatusDetailsStr    OBJECT-TYPE
        SYNTAX          DisplayString
        MAX-ACCESS      read-only
        STATUS          current
        DESCRIPTION
        "iseVolume18 Volume Current Status Details string - longer description when status is not Operational"
        ::= { iseVolume18 12 }    -- 1.3.6.1.4.1.2366.6.1.2.1.8.18.12.0
 
iseVolume18IsSnapshot    OBJECT-TYPE
        SYNTAX          DisplayString
        MAX-ACCESS      read-only
        STATUS          current
        DESCRIPTION
        "iseVolume18 Volume N Is a Snapshot?  value is unknown, yes, or no"
        ::= { iseVolume18 13 }    -- 1.3.6.1.4.1.2366.6.1.2.1.8.18.13.0
 
iseVolume18SnapshotChildId    OBJECT-TYPE
        SYNTAX          Integer32
        MAX-ACCESS      read-only
        STATUS          current
        DESCRIPTION
        "iseVolume18 Volumes Snapshot Child ID - value of 0 means NO Snapshot Child exists"
        ::= { iseVolume18 14 }    -- 1.3.6.1.4.1.2366.6.1.2.1.8.18.14.0
 
iseVolume18SnapshotParentId    OBJECT-TYPE
        SYNTAX          Integer32
        MAX-ACCESS      read-only
        STATUS          current
        DESCRIPTION
        "iseVolume18 Volumes Snapshot Parent ID - value of 0 means NO Snapshot Parent exists"
        ::= { iseVolume18 15 }    -- 1.3.6.1.4.1.2366.6.1.2.1.8.18.15.0
 
iseVolume19 OBJECT IDENTIFIER       ::= { iseStorageVols 19 }       -- 1.3.6.1.4.1.2366.6.1.2.1.8.19
 
iseVolume19Name    OBJECT-TYPE
        SYNTAX          DisplayString
        MAX-ACCESS      read-only
        STATUS          current
        DESCRIPTION
        "iseVolume19 Volume Name: ffx_xioB_4"
        ::= { iseVolume19 1 }    -- 1.3.6.1.4.1.2366.6.1.2.1.8.19.1.0
 
iseVolume19VpdId    OBJECT-TYPE
        SYNTAX          DisplayString
        MAX-ACCESS      read-only
        STATUS          current
        DESCRIPTION
        "iseVolume19 Volume VpdId: TBD"
        ::= { iseVolume19 2 }    -- 1.3.6.1.4.1.2366.6.1.2.1.8.19.2.0
 
iseVolume19DetailedStatus    OBJECT-TYPE
        SYNTAX          Integer32
        MAX-ACCESS      read-only
        STATUS          current
        DESCRIPTION
        "iseVolume19 Volume Detailed Status code"
        ::= { iseVolume19 3 }    -- 1.3.6.1.4.1.2366.6.1.2.1.8.19.3.0
 
iseVolume19Status    OBJECT-TYPE
        SYNTAX          Integer32
        MAX-ACCESS      read-only
        STATUS          current
        DESCRIPTION
        "iseVolume19 Volume Status"
        ::= { iseVolume19 4 }    -- 1.3.6.1.4.1.2366.6.1.2.1.8.19.4.0
 
iseVolume19Id    OBJECT-TYPE
        SYNTAX          Integer32
        MAX-ACCESS      read-only
        STATUS          current
        DESCRIPTION
        "iseVolume19 Volume Id"
        ::= { iseVolume19 5 }    -- 1.3.6.1.4.1.2366.6.1.2.1.8.19.5.0
 
iseVolume19RaidType    OBJECT-TYPE
        SYNTAX          Integer32
        MAX-ACCESS      read-only
        STATUS          current
        DESCRIPTION
        "iseVolume19 RaidType"
        ::= { iseVolume19 6 }    -- 1.3.6.1.4.1.2366.6.1.2.1.8.19.6.0
 
iseVolume19Pool    OBJECT-TYPE
        SYNTAX          Integer32
        MAX-ACCESS      read-only
        STATUS          current
        DESCRIPTION
        "iseVolume19 Storage Pool this volume was created from"
        ::= { iseVolume19 7 }    -- 1.3.6.1.4.1.2366.6.1.2.1.8.19.7.0
 
iseVolume19AllocationType    OBJECT-TYPE
        SYNTAX          Integer32
        MAX-ACCESS      read-only
        STATUS          current
        DESCRIPTION
        "iseVolume19 Allocation Type"
        ::= { iseVolume19 8 }    -- 1.3.6.1.4.1.2366.6.1.2.1.8.19.8.0
 
iseVolume19CacheType    OBJECT-TYPE
        SYNTAX          DisplayString
        MAX-ACCESS      read-only
        STATUS          current
        DESCRIPTION
        "iseVolume19 Volume Cache Type"
        ::= { iseVolume19 9 }    -- 1.3.6.1.4.1.2366.6.1.2.1.8.19.9.0
 
iseVolume19Size    OBJECT-TYPE
        SYNTAX          Integer32
        MAX-ACCESS      read-only
        STATUS          current
        DESCRIPTION
        "iseVolume19 Volume Size in GB"
        ::= { iseVolume19 10 }    -- 1.3.6.1.4.1.2366.6.1.2.1.8.19.10.0
 
iseVolume19StatusStr    OBJECT-TYPE
        SYNTAX          DisplayString
        MAX-ACCESS      read-only
        STATUS          current
        DESCRIPTION
        "iseVolume19 Current Status string - short description"
        ::= { iseVolume19 11 }    -- 1.3.6.1.4.1.2366.6.1.2.1.8.19.11.0
 
iseVolume19StatusDetailsStr    OBJECT-TYPE
        SYNTAX          DisplayString
        MAX-ACCESS      read-only
        STATUS          current
        DESCRIPTION
        "iseVolume19 Volume Current Status Details string - longer description when status is not Operational"
        ::= { iseVolume19 12 }    -- 1.3.6.1.4.1.2366.6.1.2.1.8.19.12.0
 
iseVolume19IsSnapshot    OBJECT-TYPE
        SYNTAX          DisplayString
        MAX-ACCESS      read-only
        STATUS          current
        DESCRIPTION
        "iseVolume19 Volume N Is a Snapshot?  value is unknown, yes, or no"
        ::= { iseVolume19 13 }    -- 1.3.6.1.4.1.2366.6.1.2.1.8.19.13.0
 
iseVolume19SnapshotChildId    OBJECT-TYPE
        SYNTAX          Integer32
        MAX-ACCESS      read-only
        STATUS          current
        DESCRIPTION
        "iseVolume19 Volumes Snapshot Child ID - value of 0 means NO Snapshot Child exists"
        ::= { iseVolume19 14 }    -- 1.3.6.1.4.1.2366.6.1.2.1.8.19.14.0
 
iseVolume19SnapshotParentId    OBJECT-TYPE
        SYNTAX          Integer32
        MAX-ACCESS      read-only
        STATUS          current
        DESCRIPTION
        "iseVolume19 Volumes Snapshot Parent ID - value of 0 means NO Snapshot Parent exists"
        ::= { iseVolume19 15 }    -- 1.3.6.1.4.1.2366.6.1.2.1.8.19.15.0
 
iseVolume20 OBJECT IDENTIFIER       ::= { iseStorageVols 20 }       -- 1.3.6.1.4.1.2366.6.1.2.1.8.20
 
iseVolume20Name    OBJECT-TYPE
        SYNTAX          DisplayString
        MAX-ACCESS      read-only
        STATUS          current
        DESCRIPTION
        "iseVolume20 Volume Name: ffx_xioB_5"
        ::= { iseVolume20 1 }    -- 1.3.6.1.4.1.2366.6.1.2.1.8.20.1.0
 
iseVolume20VpdId    OBJECT-TYPE
        SYNTAX          DisplayString
        MAX-ACCESS      read-only
        STATUS          current
        DESCRIPTION
        "iseVolume20 Volume VpdId: TBD"
        ::= { iseVolume20 2 }    -- 1.3.6.1.4.1.2366.6.1.2.1.8.20.2.0
 
iseVolume20DetailedStatus    OBJECT-TYPE
        SYNTAX          Integer32
        MAX-ACCESS      read-only
        STATUS          current
        DESCRIPTION
        "iseVolume20 Volume Detailed Status code"
        ::= { iseVolume20 3 }    -- 1.3.6.1.4.1.2366.6.1.2.1.8.20.3.0
 
iseVolume20Status    OBJECT-TYPE
        SYNTAX          Integer32
        MAX-ACCESS      read-only
        STATUS          current
        DESCRIPTION
        "iseVolume20 Volume Status"
        ::= { iseVolume20 4 }    -- 1.3.6.1.4.1.2366.6.1.2.1.8.20.4.0
 
iseVolume20Id    OBJECT-TYPE
        SYNTAX          Integer32
        MAX-ACCESS      read-only
        STATUS          current
        DESCRIPTION
        "iseVolume20 Volume Id"
        ::= { iseVolume20 5 }    -- 1.3.6.1.4.1.2366.6.1.2.1.8.20.5.0
 
iseVolume20RaidType    OBJECT-TYPE
        SYNTAX          Integer32
        MAX-ACCESS      read-only
        STATUS          current
        DESCRIPTION
        "iseVolume20 RaidType"
        ::= { iseVolume20 6 }    -- 1.3.6.1.4.1.2366.6.1.2.1.8.20.6.0
 
iseVolume20Pool    OBJECT-TYPE
        SYNTAX          Integer32
        MAX-ACCESS      read-only
        STATUS          current
        DESCRIPTION
        "iseVolume20 Storage Pool this volume was created from"
        ::= { iseVolume20 7 }    -- 1.3.6.1.4.1.2366.6.1.2.1.8.20.7.0
 
iseVolume20AllocationType    OBJECT-TYPE
        SYNTAX          Integer32
        MAX-ACCESS      read-only
        STATUS          current
        DESCRIPTION
        "iseVolume20 Allocation Type"
        ::= { iseVolume20 8 }    -- 1.3.6.1.4.1.2366.6.1.2.1.8.20.8.0
 
iseVolume20CacheType    OBJECT-TYPE
        SYNTAX          DisplayString
        MAX-ACCESS      read-only
        STATUS          current
        DESCRIPTION
        "iseVolume20 Volume Cache Type"
        ::= { iseVolume20 9 }    -- 1.3.6.1.4.1.2366.6.1.2.1.8.20.9.0
 
iseVolume20Size    OBJECT-TYPE
        SYNTAX          Integer32
        MAX-ACCESS      read-only
        STATUS          current
        DESCRIPTION
        "iseVolume20 Volume Size in GB"
        ::= { iseVolume20 10 }    -- 1.3.6.1.4.1.2366.6.1.2.1.8.20.10.0
 
iseVolume20StatusStr    OBJECT-TYPE
        SYNTAX          DisplayString
        MAX-ACCESS      read-only
        STATUS          current
        DESCRIPTION
        "iseVolume20 Current Status string - short description"
        ::= { iseVolume20 11 }    -- 1.3.6.1.4.1.2366.6.1.2.1.8.20.11.0
 
iseVolume20StatusDetailsStr    OBJECT-TYPE
        SYNTAX          DisplayString
        MAX-ACCESS      read-only
        STATUS          current
        DESCRIPTION
        "iseVolume20 Volume Current Status Details string - longer description when status is not Operational"
        ::= { iseVolume20 12 }    -- 1.3.6.1.4.1.2366.6.1.2.1.8.20.12.0
 
iseVolume20IsSnapshot    OBJECT-TYPE
        SYNTAX          DisplayString
        MAX-ACCESS      read-only
        STATUS          current
        DESCRIPTION
        "iseVolume20 Volume N Is a Snapshot?  value is unknown, yes, or no"
        ::= { iseVolume20 13 }    -- 1.3.6.1.4.1.2366.6.1.2.1.8.20.13.0
 
iseVolume20SnapshotChildId    OBJECT-TYPE
        SYNTAX          Integer32
        MAX-ACCESS      read-only
        STATUS          current
        DESCRIPTION
        "iseVolume20 Volumes Snapshot Child ID - value of 0 means NO Snapshot Child exists"
        ::= { iseVolume20 14 }    -- 1.3.6.1.4.1.2366.6.1.2.1.8.20.14.0
 
iseVolume20SnapshotParentId    OBJECT-TYPE
        SYNTAX          Integer32
        MAX-ACCESS      read-only
        STATUS          current
        DESCRIPTION
        "iseVolume20 Volumes Snapshot Parent ID - value of 0 means NO Snapshot Parent exists"
        ::= { iseVolume20 15 }    -- 1.3.6.1.4.1.2366.6.1.2.1.8.20.15.0
 
iseVolume21 OBJECT IDENTIFIER       ::= { iseStorageVols 21 }       -- 1.3.6.1.4.1.2366.6.1.2.1.8.21
 
iseVolume21Name    OBJECT-TYPE
        SYNTAX          DisplayString
        MAX-ACCESS      read-only
        STATUS          current
        DESCRIPTION
        "iseVolume21 Volume Name: ffx_xioB_6"
        ::= { iseVolume21 1 }    -- 1.3.6.1.4.1.2366.6.1.2.1.8.21.1.0
 
iseVolume21VpdId    OBJECT-TYPE
        SYNTAX          DisplayString
        MAX-ACCESS      read-only
        STATUS          current
        DESCRIPTION
        "iseVolume21 Volume VpdId: TBD"
        ::= { iseVolume21 2 }    -- 1.3.6.1.4.1.2366.6.1.2.1.8.21.2.0
 
iseVolume21DetailedStatus    OBJECT-TYPE
        SYNTAX          Integer32
        MAX-ACCESS      read-only
        STATUS          current
        DESCRIPTION
        "iseVolume21 Volume Detailed Status code"
        ::= { iseVolume21 3 }    -- 1.3.6.1.4.1.2366.6.1.2.1.8.21.3.0
 
iseVolume21Status    OBJECT-TYPE
        SYNTAX          Integer32
        MAX-ACCESS      read-only
        STATUS          current
        DESCRIPTION
        "iseVolume21 Volume Status"
        ::= { iseVolume21 4 }    -- 1.3.6.1.4.1.2366.6.1.2.1.8.21.4.0
 
iseVolume21Id    OBJECT-TYPE
        SYNTAX          Integer32
        MAX-ACCESS      read-only
        STATUS          current
        DESCRIPTION
        "iseVolume21 Volume Id"
        ::= { iseVolume21 5 }    -- 1.3.6.1.4.1.2366.6.1.2.1.8.21.5.0
 
iseVolume21RaidType    OBJECT-TYPE
        SYNTAX          Integer32
        MAX-ACCESS      read-only
        STATUS          current
        DESCRIPTION
        "iseVolume21 RaidType"
        ::= { iseVolume21 6 }    -- 1.3.6.1.4.1.2366.6.1.2.1.8.21.6.0
 
iseVolume21Pool    OBJECT-TYPE
        SYNTAX          Integer32
        MAX-ACCESS      read-only
        STATUS          current
        DESCRIPTION
        "iseVolume21 Storage Pool this volume was created from"
        ::= { iseVolume21 7 }    -- 1.3.6.1.4.1.2366.6.1.2.1.8.21.7.0
 
iseVolume21AllocationType    OBJECT-TYPE
        SYNTAX          Integer32
        MAX-ACCESS      read-only
        STATUS          current
        DESCRIPTION
        "iseVolume21 Allocation Type"
        ::= { iseVolume21 8 }    -- 1.3.6.1.4.1.2366.6.1.2.1.8.21.8.0
 
iseVolume21CacheType    OBJECT-TYPE
        SYNTAX          DisplayString
        MAX-ACCESS      read-only
        STATUS          current
        DESCRIPTION
        "iseVolume21 Volume Cache Type"
        ::= { iseVolume21 9 }    -- 1.3.6.1.4.1.2366.6.1.2.1.8.21.9.0
 
iseVolume21Size    OBJECT-TYPE
        SYNTAX          Integer32
        MAX-ACCESS      read-only
        STATUS          current
        DESCRIPTION
        "iseVolume21 Volume Size in GB"
        ::= { iseVolume21 10 }    -- 1.3.6.1.4.1.2366.6.1.2.1.8.21.10.0
 
iseVolume21StatusStr    OBJECT-TYPE
        SYNTAX          DisplayString
        MAX-ACCESS      read-only
        STATUS          current
        DESCRIPTION
        "iseVolume21 Current Status string - short description"
        ::= { iseVolume21 11 }    -- 1.3.6.1.4.1.2366.6.1.2.1.8.21.11.0
 
iseVolume21StatusDetailsStr    OBJECT-TYPE
        SYNTAX          DisplayString
        MAX-ACCESS      read-only
        STATUS          current
        DESCRIPTION
        "iseVolume21 Volume Current Status Details string - longer description when status is not Operational"
        ::= { iseVolume21 12 }    -- 1.3.6.1.4.1.2366.6.1.2.1.8.21.12.0
 
iseVolume21IsSnapshot    OBJECT-TYPE
        SYNTAX          DisplayString
        MAX-ACCESS      read-only
        STATUS          current
        DESCRIPTION
        "iseVolume21 Volume N Is a Snapshot?  value is unknown, yes, or no"
        ::= { iseVolume21 13 }    -- 1.3.6.1.4.1.2366.6.1.2.1.8.21.13.0
 
iseVolume21SnapshotChildId    OBJECT-TYPE
        SYNTAX          Integer32
        MAX-ACCESS      read-only
        STATUS          current
        DESCRIPTION
        "iseVolume21 Volumes Snapshot Child ID - value of 0 means NO Snapshot Child exists"
        ::= { iseVolume21 14 }    -- 1.3.6.1.4.1.2366.6.1.2.1.8.21.14.0
 
iseVolume21SnapshotParentId    OBJECT-TYPE
        SYNTAX          Integer32
        MAX-ACCESS      read-only
        STATUS          current
        DESCRIPTION
        "iseVolume21 Volumes Snapshot Parent ID - value of 0 means NO Snapshot Parent exists"
        ::= { iseVolume21 15 }    -- 1.3.6.1.4.1.2366.6.1.2.1.8.21.15.0
 
iseVolume22 OBJECT IDENTIFIER       ::= { iseStorageVols 22 }       -- 1.3.6.1.4.1.2366.6.1.2.1.8.22
 
iseVolume22Name    OBJECT-TYPE
        SYNTAX          DisplayString
        MAX-ACCESS      read-only
        STATUS          current
        DESCRIPTION
        "iseVolume22 Volume Name: ffx_xioB_7"
        ::= { iseVolume22 1 }    -- 1.3.6.1.4.1.2366.6.1.2.1.8.22.1.0
 
iseVolume22VpdId    OBJECT-TYPE
        SYNTAX          DisplayString
        MAX-ACCESS      read-only
        STATUS          current
        DESCRIPTION
        "iseVolume22 Volume VpdId: TBD"
        ::= { iseVolume22 2 }    -- 1.3.6.1.4.1.2366.6.1.2.1.8.22.2.0
 
iseVolume22DetailedStatus    OBJECT-TYPE
        SYNTAX          Integer32
        MAX-ACCESS      read-only
        STATUS          current
        DESCRIPTION
        "iseVolume22 Volume Detailed Status code"
        ::= { iseVolume22 3 }    -- 1.3.6.1.4.1.2366.6.1.2.1.8.22.3.0
 
iseVolume22Status    OBJECT-TYPE
        SYNTAX          Integer32
        MAX-ACCESS      read-only
        STATUS          current
        DESCRIPTION
        "iseVolume22 Volume Status"
        ::= { iseVolume22 4 }    -- 1.3.6.1.4.1.2366.6.1.2.1.8.22.4.0
 
iseVolume22Id    OBJECT-TYPE
        SYNTAX          Integer32
        MAX-ACCESS      read-only
        STATUS          current
        DESCRIPTION
        "iseVolume22 Volume Id"
        ::= { iseVolume22 5 }    -- 1.3.6.1.4.1.2366.6.1.2.1.8.22.5.0
 
iseVolume22RaidType    OBJECT-TYPE
        SYNTAX          Integer32
        MAX-ACCESS      read-only
        STATUS          current
        DESCRIPTION
        "iseVolume22 RaidType"
        ::= { iseVolume22 6 }    -- 1.3.6.1.4.1.2366.6.1.2.1.8.22.6.0
 
iseVolume22Pool    OBJECT-TYPE
        SYNTAX          Integer32
        MAX-ACCESS      read-only
        STATUS          current
        DESCRIPTION
        "iseVolume22 Storage Pool this volume was created from"
        ::= { iseVolume22 7 }    -- 1.3.6.1.4.1.2366.6.1.2.1.8.22.7.0
 
iseVolume22AllocationType    OBJECT-TYPE
        SYNTAX          Integer32
        MAX-ACCESS      read-only
        STATUS          current
        DESCRIPTION
        "iseVolume22 Allocation Type"
        ::= { iseVolume22 8 }    -- 1.3.6.1.4.1.2366.6.1.2.1.8.22.8.0
 
iseVolume22CacheType    OBJECT-TYPE
        SYNTAX          DisplayString
        MAX-ACCESS      read-only
        STATUS          current
        DESCRIPTION
        "iseVolume22 Volume Cache Type"
        ::= { iseVolume22 9 }    -- 1.3.6.1.4.1.2366.6.1.2.1.8.22.9.0
 
iseVolume22Size    OBJECT-TYPE
        SYNTAX          Integer32
        MAX-ACCESS      read-only
        STATUS          current
        DESCRIPTION
        "iseVolume22 Volume Size in GB"
        ::= { iseVolume22 10 }    -- 1.3.6.1.4.1.2366.6.1.2.1.8.22.10.0
 
iseVolume22StatusStr    OBJECT-TYPE
        SYNTAX          DisplayString
        MAX-ACCESS      read-only
        STATUS          current
        DESCRIPTION
        "iseVolume22 Current Status string - short description"
        ::= { iseVolume22 11 }    -- 1.3.6.1.4.1.2366.6.1.2.1.8.22.11.0
 
iseVolume22StatusDetailsStr    OBJECT-TYPE
        SYNTAX          DisplayString
        MAX-ACCESS      read-only
        STATUS          current
        DESCRIPTION
        "iseVolume22 Volume Current Status Details string - longer description when status is not Operational"
        ::= { iseVolume22 12 }    -- 1.3.6.1.4.1.2366.6.1.2.1.8.22.12.0
 
iseVolume22IsSnapshot    OBJECT-TYPE
        SYNTAX          DisplayString
        MAX-ACCESS      read-only
        STATUS          current
        DESCRIPTION
        "iseVolume22 Volume N Is a Snapshot?  value is unknown, yes, or no"
        ::= { iseVolume22 13 }    -- 1.3.6.1.4.1.2366.6.1.2.1.8.22.13.0
 
iseVolume22SnapshotChildId    OBJECT-TYPE
        SYNTAX          Integer32
        MAX-ACCESS      read-only
        STATUS          current
        DESCRIPTION
        "iseVolume22 Volumes Snapshot Child ID - value of 0 means NO Snapshot Child exists"
        ::= { iseVolume22 14 }    -- 1.3.6.1.4.1.2366.6.1.2.1.8.22.14.0
 
iseVolume22SnapshotParentId    OBJECT-TYPE
        SYNTAX          Integer32
        MAX-ACCESS      read-only
        STATUS          current
        DESCRIPTION
        "iseVolume22 Volumes Snapshot Parent ID - value of 0 means NO Snapshot Parent exists"
        ::= { iseVolume22 15 }    -- 1.3.6.1.4.1.2366.6.1.2.1.8.22.15.0
 
iseVolume23 OBJECT IDENTIFIER       ::= { iseStorageVols 23 }       -- 1.3.6.1.4.1.2366.6.1.2.1.8.23
 
iseVolume23Name    OBJECT-TYPE
        SYNTAX          DisplayString
        MAX-ACCESS      read-only
        STATUS          current
        DESCRIPTION
        "iseVolume23 Volume Name: ffx_xioB_8"
        ::= { iseVolume23 1 }    -- 1.3.6.1.4.1.2366.6.1.2.1.8.23.1.0
 
iseVolume23VpdId    OBJECT-TYPE
        SYNTAX          DisplayString
        MAX-ACCESS      read-only
        STATUS          current
        DESCRIPTION
        "iseVolume23 Volume VpdId: TBD"
        ::= { iseVolume23 2 }    -- 1.3.6.1.4.1.2366.6.1.2.1.8.23.2.0
 
iseVolume23DetailedStatus    OBJECT-TYPE
        SYNTAX          Integer32
        MAX-ACCESS      read-only
        STATUS          current
        DESCRIPTION
        "iseVolume23 Volume Detailed Status code"
        ::= { iseVolume23 3 }    -- 1.3.6.1.4.1.2366.6.1.2.1.8.23.3.0
 
iseVolume23Status    OBJECT-TYPE
        SYNTAX          Integer32
        MAX-ACCESS      read-only
        STATUS          current
        DESCRIPTION
        "iseVolume23 Volume Status"
        ::= { iseVolume23 4 }    -- 1.3.6.1.4.1.2366.6.1.2.1.8.23.4.0
 
iseVolume23Id    OBJECT-TYPE
        SYNTAX          Integer32
        MAX-ACCESS      read-only
        STATUS          current
        DESCRIPTION
        "iseVolume23 Volume Id"
        ::= { iseVolume23 5 }    -- 1.3.6.1.4.1.2366.6.1.2.1.8.23.5.0
 
iseVolume23RaidType    OBJECT-TYPE
        SYNTAX          Integer32
        MAX-ACCESS      read-only
        STATUS          current
        DESCRIPTION
        "iseVolume23 RaidType"
        ::= { iseVolume23 6 }    -- 1.3.6.1.4.1.2366.6.1.2.1.8.23.6.0
 
iseVolume23Pool    OBJECT-TYPE
        SYNTAX          Integer32
        MAX-ACCESS      read-only
        STATUS          current
        DESCRIPTION
        "iseVolume23 Storage Pool this volume was created from"
        ::= { iseVolume23 7 }    -- 1.3.6.1.4.1.2366.6.1.2.1.8.23.7.0
 
iseVolume23AllocationType    OBJECT-TYPE
        SYNTAX          Integer32
        MAX-ACCESS      read-only
        STATUS          current
        DESCRIPTION
        "iseVolume23 Allocation Type"
        ::= { iseVolume23 8 }    -- 1.3.6.1.4.1.2366.6.1.2.1.8.23.8.0
 
iseVolume23CacheType    OBJECT-TYPE
        SYNTAX          DisplayString
        MAX-ACCESS      read-only
        STATUS          current
        DESCRIPTION
        "iseVolume23 Volume Cache Type"
        ::= { iseVolume23 9 }    -- 1.3.6.1.4.1.2366.6.1.2.1.8.23.9.0
 
iseVolume23Size    OBJECT-TYPE
        SYNTAX          Integer32
        MAX-ACCESS      read-only
        STATUS          current
        DESCRIPTION
        "iseVolume23 Volume Size in GB"
        ::= { iseVolume23 10 }    -- 1.3.6.1.4.1.2366.6.1.2.1.8.23.10.0
 
iseVolume23StatusStr    OBJECT-TYPE
        SYNTAX          DisplayString
        MAX-ACCESS      read-only
        STATUS          current
        DESCRIPTION
        "iseVolume23 Current Status string - short description"
        ::= { iseVolume23 11 }    -- 1.3.6.1.4.1.2366.6.1.2.1.8.23.11.0
 
iseVolume23StatusDetailsStr    OBJECT-TYPE
        SYNTAX          DisplayString
        MAX-ACCESS      read-only
        STATUS          current
        DESCRIPTION
        "iseVolume23 Volume Current Status Details string - longer description when status is not Operational"
        ::= { iseVolume23 12 }    -- 1.3.6.1.4.1.2366.6.1.2.1.8.23.12.0
 
iseVolume23IsSnapshot    OBJECT-TYPE
        SYNTAX          DisplayString
        MAX-ACCESS      read-only
        STATUS          current
        DESCRIPTION
        "iseVolume23 Volume N Is a Snapshot?  value is unknown, yes, or no"
        ::= { iseVolume23 13 }    -- 1.3.6.1.4.1.2366.6.1.2.1.8.23.13.0
 
iseVolume23SnapshotChildId    OBJECT-TYPE
        SYNTAX          Integer32
        MAX-ACCESS      read-only
        STATUS          current
        DESCRIPTION
        "iseVolume23 Volumes Snapshot Child ID - value of 0 means NO Snapshot Child exists"
        ::= { iseVolume23 14 }    -- 1.3.6.1.4.1.2366.6.1.2.1.8.23.14.0
 
iseVolume23SnapshotParentId    OBJECT-TYPE
        SYNTAX          Integer32
        MAX-ACCESS      read-only
        STATUS          current
        DESCRIPTION
        "iseVolume23 Volumes Snapshot Parent ID - value of 0 means NO Snapshot Parent exists"
        ::= { iseVolume23 15 }    -- 1.3.6.1.4.1.2366.6.1.2.1.8.23.15.0
 
iseVolume24 OBJECT IDENTIFIER       ::= { iseStorageVols 24 }       -- 1.3.6.1.4.1.2366.6.1.2.1.8.24
 
iseVolume24Name    OBJECT-TYPE
        SYNTAX          DisplayString
        MAX-ACCESS      read-only
        STATUS          current
        DESCRIPTION
        "iseVolume24 Volume Name: ffx_xioB_9"
        ::= { iseVolume24 1 }    -- 1.3.6.1.4.1.2366.6.1.2.1.8.24.1.0
 
iseVolume24VpdId    OBJECT-TYPE
        SYNTAX          DisplayString
        MAX-ACCESS      read-only
        STATUS          current
        DESCRIPTION
        "iseVolume24 Volume VpdId: TBD"
        ::= { iseVolume24 2 }    -- 1.3.6.1.4.1.2366.6.1.2.1.8.24.2.0
 
iseVolume24DetailedStatus    OBJECT-TYPE
        SYNTAX          Integer32
        MAX-ACCESS      read-only
        STATUS          current
        DESCRIPTION
        "iseVolume24 Volume Detailed Status code"
        ::= { iseVolume24 3 }    -- 1.3.6.1.4.1.2366.6.1.2.1.8.24.3.0
 
iseVolume24Status    OBJECT-TYPE
        SYNTAX          Integer32
        MAX-ACCESS      read-only
        STATUS          current
        DESCRIPTION
        "iseVolume24 Volume Status"
        ::= { iseVolume24 4 }    -- 1.3.6.1.4.1.2366.6.1.2.1.8.24.4.0
 
iseVolume24Id    OBJECT-TYPE
        SYNTAX          Integer32
        MAX-ACCESS      read-only
        STATUS          current
        DESCRIPTION
        "iseVolume24 Volume Id"
        ::= { iseVolume24 5 }    -- 1.3.6.1.4.1.2366.6.1.2.1.8.24.5.0
 
iseVolume24RaidType    OBJECT-TYPE
        SYNTAX          Integer32
        MAX-ACCESS      read-only
        STATUS          current
        DESCRIPTION
        "iseVolume24 RaidType"
        ::= { iseVolume24 6 }    -- 1.3.6.1.4.1.2366.6.1.2.1.8.24.6.0
 
iseVolume24Pool    OBJECT-TYPE
        SYNTAX          Integer32
        MAX-ACCESS      read-only
        STATUS          current
        DESCRIPTION
        "iseVolume24 Storage Pool this volume was created from"
        ::= { iseVolume24 7 }    -- 1.3.6.1.4.1.2366.6.1.2.1.8.24.7.0
 
iseVolume24AllocationType    OBJECT-TYPE
        SYNTAX          Integer32
        MAX-ACCESS      read-only
        STATUS          current
        DESCRIPTION
        "iseVolume24 Allocation Type"
        ::= { iseVolume24 8 }    -- 1.3.6.1.4.1.2366.6.1.2.1.8.24.8.0
 
iseVolume24CacheType    OBJECT-TYPE
        SYNTAX          DisplayString
        MAX-ACCESS      read-only
        STATUS          current
        DESCRIPTION
        "iseVolume24 Volume Cache Type"
        ::= { iseVolume24 9 }    -- 1.3.6.1.4.1.2366.6.1.2.1.8.24.9.0
 
iseVolume24Size    OBJECT-TYPE
        SYNTAX          Integer32
        MAX-ACCESS      read-only
        STATUS          current
        DESCRIPTION
        "iseVolume24 Volume Size in GB"
        ::= { iseVolume24 10 }    -- 1.3.6.1.4.1.2366.6.1.2.1.8.24.10.0
 
iseVolume24StatusStr    OBJECT-TYPE
        SYNTAX          DisplayString
        MAX-ACCESS      read-only
        STATUS          current
        DESCRIPTION
        "iseVolume24 Current Status string - short description"
        ::= { iseVolume24 11 }    -- 1.3.6.1.4.1.2366.6.1.2.1.8.24.11.0
 
iseVolume24StatusDetailsStr    OBJECT-TYPE
        SYNTAX          DisplayString
        MAX-ACCESS      read-only
        STATUS          current
        DESCRIPTION
        "iseVolume24 Volume Current Status Details string - longer description when status is not Operational"
        ::= { iseVolume24 12 }    -- 1.3.6.1.4.1.2366.6.1.2.1.8.24.12.0
 
iseVolume24IsSnapshot    OBJECT-TYPE
        SYNTAX          DisplayString
        MAX-ACCESS      read-only
        STATUS          current
        DESCRIPTION
        "iseVolume24 Volume N Is a Snapshot?  value is unknown, yes, or no"
        ::= { iseVolume24 13 }    -- 1.3.6.1.4.1.2366.6.1.2.1.8.24.13.0
 
iseVolume24SnapshotChildId    OBJECT-TYPE
        SYNTAX          Integer32
        MAX-ACCESS      read-only
        STATUS          current
        DESCRIPTION
        "iseVolume24 Volumes Snapshot Child ID - value of 0 means NO Snapshot Child exists"
        ::= { iseVolume24 14 }    -- 1.3.6.1.4.1.2366.6.1.2.1.8.24.14.0
 
iseVolume24SnapshotParentId    OBJECT-TYPE
        SYNTAX          Integer32
        MAX-ACCESS      read-only
        STATUS          current
        DESCRIPTION
        "iseVolume24 Volumes Snapshot Parent ID - value of 0 means NO Snapshot Parent exists"
        ::= { iseVolume24 15 }    -- 1.3.6.1.4.1.2366.6.1.2.1.8.24.15.0
 
iseVolume25 OBJECT IDENTIFIER       ::= { iseStorageVols 25 }       -- 1.3.6.1.4.1.2366.6.1.2.1.8.25
 
iseVolume25Name    OBJECT-TYPE
        SYNTAX          DisplayString
        MAX-ACCESS      read-only
        STATUS          current
        DESCRIPTION
        "iseVolume25 Volume Name: ffx_xioB_10"
        ::= { iseVolume25 1 }    -- 1.3.6.1.4.1.2366.6.1.2.1.8.25.1.0
 
iseVolume25VpdId    OBJECT-TYPE
        SYNTAX          DisplayString
        MAX-ACCESS      read-only
        STATUS          current
        DESCRIPTION
        "iseVolume25 Volume VpdId: TBD"
        ::= { iseVolume25 2 }    -- 1.3.6.1.4.1.2366.6.1.2.1.8.25.2.0
 
iseVolume25DetailedStatus    OBJECT-TYPE
        SYNTAX          Integer32
        MAX-ACCESS      read-only
        STATUS          current
        DESCRIPTION
        "iseVolume25 Volume Detailed Status code"
        ::= { iseVolume25 3 }    -- 1.3.6.1.4.1.2366.6.1.2.1.8.25.3.0
 
iseVolume25Status    OBJECT-TYPE
        SYNTAX          Integer32
        MAX-ACCESS      read-only
        STATUS          current
        DESCRIPTION
        "iseVolume25 Volume Status"
        ::= { iseVolume25 4 }    -- 1.3.6.1.4.1.2366.6.1.2.1.8.25.4.0
 
iseVolume25Id    OBJECT-TYPE
        SYNTAX          Integer32
        MAX-ACCESS      read-only
        STATUS          current
        DESCRIPTION
        "iseVolume25 Volume Id"
        ::= { iseVolume25 5 }    -- 1.3.6.1.4.1.2366.6.1.2.1.8.25.5.0
 
iseVolume25RaidType    OBJECT-TYPE
        SYNTAX          Integer32
        MAX-ACCESS      read-only
        STATUS          current
        DESCRIPTION
        "iseVolume25 RaidType"
        ::= { iseVolume25 6 }    -- 1.3.6.1.4.1.2366.6.1.2.1.8.25.6.0
 
iseVolume25Pool    OBJECT-TYPE
        SYNTAX          Integer32
        MAX-ACCESS      read-only
        STATUS          current
        DESCRIPTION
        "iseVolume25 Storage Pool this volume was created from"
        ::= { iseVolume25 7 }    -- 1.3.6.1.4.1.2366.6.1.2.1.8.25.7.0
 
iseVolume25AllocationType    OBJECT-TYPE
        SYNTAX          Integer32
        MAX-ACCESS      read-only
        STATUS          current
        DESCRIPTION
        "iseVolume25 Allocation Type"
        ::= { iseVolume25 8 }    -- 1.3.6.1.4.1.2366.6.1.2.1.8.25.8.0
 
iseVolume25CacheType    OBJECT-TYPE
        SYNTAX          DisplayString
        MAX-ACCESS      read-only
        STATUS          current
        DESCRIPTION
        "iseVolume25 Volume Cache Type"
        ::= { iseVolume25 9 }    -- 1.3.6.1.4.1.2366.6.1.2.1.8.25.9.0
 
iseVolume25Size    OBJECT-TYPE
        SYNTAX          Integer32
        MAX-ACCESS      read-only
        STATUS          current
        DESCRIPTION
        "iseVolume25 Volume Size in GB"
        ::= { iseVolume25 10 }    -- 1.3.6.1.4.1.2366.6.1.2.1.8.25.10.0
 
iseVolume25StatusStr    OBJECT-TYPE
        SYNTAX          DisplayString
        MAX-ACCESS      read-only
        STATUS          current
        DESCRIPTION
        "iseVolume25 Current Status string - short description"
        ::= { iseVolume25 11 }    -- 1.3.6.1.4.1.2366.6.1.2.1.8.25.11.0
 
iseVolume25StatusDetailsStr    OBJECT-TYPE
        SYNTAX          DisplayString
        MAX-ACCESS      read-only
        STATUS          current
        DESCRIPTION
        "iseVolume25 Volume Current Status Details string - longer description when status is not Operational"
        ::= { iseVolume25 12 }    -- 1.3.6.1.4.1.2366.6.1.2.1.8.25.12.0
 
iseVolume25IsSnapshot    OBJECT-TYPE
        SYNTAX          DisplayString
        MAX-ACCESS      read-only
        STATUS          current
        DESCRIPTION
        "iseVolume25 Volume N Is a Snapshot?  value is unknown, yes, or no"
        ::= { iseVolume25 13 }    -- 1.3.6.1.4.1.2366.6.1.2.1.8.25.13.0
 
iseVolume25SnapshotChildId    OBJECT-TYPE
        SYNTAX          Integer32
        MAX-ACCESS      read-only
        STATUS          current
        DESCRIPTION
        "iseVolume25 Volumes Snapshot Child ID - value of 0 means NO Snapshot Child exists"
        ::= { iseVolume25 14 }    -- 1.3.6.1.4.1.2366.6.1.2.1.8.25.14.0
 
iseVolume25SnapshotParentId    OBJECT-TYPE
        SYNTAX          Integer32
        MAX-ACCESS      read-only
        STATUS          current
        DESCRIPTION
        "iseVolume25 Volumes Snapshot Parent ID - value of 0 means NO Snapshot Parent exists"
        ::= { iseVolume25 15 }    -- 1.3.6.1.4.1.2366.6.1.2.1.8.25.15.0
 
iseVolume26 OBJECT IDENTIFIER       ::= { iseStorageVols 26 }       -- 1.3.6.1.4.1.2366.6.1.2.1.8.26
 
iseVolume26Name    OBJECT-TYPE
        SYNTAX          DisplayString
        MAX-ACCESS      read-only
        STATUS          current
        DESCRIPTION
        "iseVolume26 Volume Name: ffx_xioB_11"
        ::= { iseVolume26 1 }    -- 1.3.6.1.4.1.2366.6.1.2.1.8.26.1.0
 
iseVolume26VpdId    OBJECT-TYPE
        SYNTAX          DisplayString
        MAX-ACCESS      read-only
        STATUS          current
        DESCRIPTION
        "iseVolume26 Volume VpdId: TBD"
        ::= { iseVolume26 2 }    -- 1.3.6.1.4.1.2366.6.1.2.1.8.26.2.0
 
iseVolume26DetailedStatus    OBJECT-TYPE
        SYNTAX          Integer32
        MAX-ACCESS      read-only
        STATUS          current
        DESCRIPTION
        "iseVolume26 Volume Detailed Status code"
        ::= { iseVolume26 3 }    -- 1.3.6.1.4.1.2366.6.1.2.1.8.26.3.0
 
iseVolume26Status    OBJECT-TYPE
        SYNTAX          Integer32
        MAX-ACCESS      read-only
        STATUS          current
        DESCRIPTION
        "iseVolume26 Volume Status"
        ::= { iseVolume26 4 }    -- 1.3.6.1.4.1.2366.6.1.2.1.8.26.4.0
 
iseVolume26Id    OBJECT-TYPE
        SYNTAX          Integer32
        MAX-ACCESS      read-only
        STATUS          current
        DESCRIPTION
        "iseVolume26 Volume Id"
        ::= { iseVolume26 5 }    -- 1.3.6.1.4.1.2366.6.1.2.1.8.26.5.0
 
iseVolume26RaidType    OBJECT-TYPE
        SYNTAX          Integer32
        MAX-ACCESS      read-only
        STATUS          current
        DESCRIPTION
        "iseVolume26 RaidType"
        ::= { iseVolume26 6 }    -- 1.3.6.1.4.1.2366.6.1.2.1.8.26.6.0
 
iseVolume26Pool    OBJECT-TYPE
        SYNTAX          Integer32
        MAX-ACCESS      read-only
        STATUS          current
        DESCRIPTION
        "iseVolume26 Storage Pool this volume was created from"
        ::= { iseVolume26 7 }    -- 1.3.6.1.4.1.2366.6.1.2.1.8.26.7.0
 
iseVolume26AllocationType    OBJECT-TYPE
        SYNTAX          Integer32
        MAX-ACCESS      read-only
        STATUS          current
        DESCRIPTION
        "iseVolume26 Allocation Type"
        ::= { iseVolume26 8 }    -- 1.3.6.1.4.1.2366.6.1.2.1.8.26.8.0
 
iseVolume26CacheType    OBJECT-TYPE
        SYNTAX          DisplayString
        MAX-ACCESS      read-only
        STATUS          current
        DESCRIPTION
        "iseVolume26 Volume Cache Type"
        ::= { iseVolume26 9 }    -- 1.3.6.1.4.1.2366.6.1.2.1.8.26.9.0
 
iseVolume26Size    OBJECT-TYPE
        SYNTAX          Integer32
        MAX-ACCESS      read-only
        STATUS          current
        DESCRIPTION
        "iseVolume26 Volume Size in GB"
        ::= { iseVolume26 10 }    -- 1.3.6.1.4.1.2366.6.1.2.1.8.26.10.0
 
iseVolume26StatusStr    OBJECT-TYPE
        SYNTAX          DisplayString
        MAX-ACCESS      read-only
        STATUS          current
        DESCRIPTION
        "iseVolume26 Current Status string - short description"
        ::= { iseVolume26 11 }    -- 1.3.6.1.4.1.2366.6.1.2.1.8.26.11.0
 
iseVolume26StatusDetailsStr    OBJECT-TYPE
        SYNTAX          DisplayString
        MAX-ACCESS      read-only
        STATUS          current
        DESCRIPTION
        "iseVolume26 Volume Current Status Details string - longer description when status is not Operational"
        ::= { iseVolume26 12 }    -- 1.3.6.1.4.1.2366.6.1.2.1.8.26.12.0
 
iseVolume26IsSnapshot    OBJECT-TYPE
        SYNTAX          DisplayString
        MAX-ACCESS      read-only
        STATUS          current
        DESCRIPTION
        "iseVolume26 Volume N Is a Snapshot?  value is unknown, yes, or no"
        ::= { iseVolume26 13 }    -- 1.3.6.1.4.1.2366.6.1.2.1.8.26.13.0
 
iseVolume26SnapshotChildId    OBJECT-TYPE
        SYNTAX          Integer32
        MAX-ACCESS      read-only
        STATUS          current
        DESCRIPTION
        "iseVolume26 Volumes Snapshot Child ID - value of 0 means NO Snapshot Child exists"
        ::= { iseVolume26 14 }    -- 1.3.6.1.4.1.2366.6.1.2.1.8.26.14.0
 
iseVolume26SnapshotParentId    OBJECT-TYPE
        SYNTAX          Integer32
        MAX-ACCESS      read-only
        STATUS          current
        DESCRIPTION
        "iseVolume26 Volumes Snapshot Parent ID - value of 0 means NO Snapshot Parent exists"
        ::= { iseVolume26 15 }    -- 1.3.6.1.4.1.2366.6.1.2.1.8.26.15.0
 
iseVolume27 OBJECT IDENTIFIER       ::= { iseStorageVols 27 }       -- 1.3.6.1.4.1.2366.6.1.2.1.8.27
 
iseVolume27Name    OBJECT-TYPE
        SYNTAX          DisplayString
        MAX-ACCESS      read-only
        STATUS          current
        DESCRIPTION
        "iseVolume27 Volume Name: ffx_xioB_12"
        ::= { iseVolume27 1 }    -- 1.3.6.1.4.1.2366.6.1.2.1.8.27.1.0
 
iseVolume27VpdId    OBJECT-TYPE
        SYNTAX          DisplayString
        MAX-ACCESS      read-only
        STATUS          current
        DESCRIPTION
        "iseVolume27 Volume VpdId: TBD"
        ::= { iseVolume27 2 }    -- 1.3.6.1.4.1.2366.6.1.2.1.8.27.2.0
 
iseVolume27DetailedStatus    OBJECT-TYPE
        SYNTAX          Integer32
        MAX-ACCESS      read-only
        STATUS          current
        DESCRIPTION
        "iseVolume27 Volume Detailed Status code"
        ::= { iseVolume27 3 }    -- 1.3.6.1.4.1.2366.6.1.2.1.8.27.3.0
 
iseVolume27Status    OBJECT-TYPE
        SYNTAX          Integer32
        MAX-ACCESS      read-only
        STATUS          current
        DESCRIPTION
        "iseVolume27 Volume Status"
        ::= { iseVolume27 4 }    -- 1.3.6.1.4.1.2366.6.1.2.1.8.27.4.0
 
iseVolume27Id    OBJECT-TYPE
        SYNTAX          Integer32
        MAX-ACCESS      read-only
        STATUS          current
        DESCRIPTION
        "iseVolume27 Volume Id"
        ::= { iseVolume27 5 }    -- 1.3.6.1.4.1.2366.6.1.2.1.8.27.5.0
 
iseVolume27RaidType    OBJECT-TYPE
        SYNTAX          Integer32
        MAX-ACCESS      read-only
        STATUS          current
        DESCRIPTION
        "iseVolume27 RaidType"
        ::= { iseVolume27 6 }    -- 1.3.6.1.4.1.2366.6.1.2.1.8.27.6.0
 
iseVolume27Pool    OBJECT-TYPE
        SYNTAX          Integer32
        MAX-ACCESS      read-only
        STATUS          current
        DESCRIPTION
        "iseVolume27 Storage Pool this volume was created from"
        ::= { iseVolume27 7 }    -- 1.3.6.1.4.1.2366.6.1.2.1.8.27.7.0
 
iseVolume27AllocationType    OBJECT-TYPE
        SYNTAX          Integer32
        MAX-ACCESS      read-only
        STATUS          current
        DESCRIPTION
        "iseVolume27 Allocation Type"
        ::= { iseVolume27 8 }    -- 1.3.6.1.4.1.2366.6.1.2.1.8.27.8.0
 
iseVolume27CacheType    OBJECT-TYPE
        SYNTAX          DisplayString
        MAX-ACCESS      read-only
        STATUS          current
        DESCRIPTION
        "iseVolume27 Volume Cache Type"
        ::= { iseVolume27 9 }    -- 1.3.6.1.4.1.2366.6.1.2.1.8.27.9.0
 
iseVolume27Size    OBJECT-TYPE
        SYNTAX          Integer32
        MAX-ACCESS      read-only
        STATUS          current
        DESCRIPTION
        "iseVolume27 Volume Size in GB"
        ::= { iseVolume27 10 }    -- 1.3.6.1.4.1.2366.6.1.2.1.8.27.10.0
 
iseVolume27StatusStr    OBJECT-TYPE
        SYNTAX          DisplayString
        MAX-ACCESS      read-only
        STATUS          current
        DESCRIPTION
        "iseVolume27 Current Status string - short description"
        ::= { iseVolume27 11 }    -- 1.3.6.1.4.1.2366.6.1.2.1.8.27.11.0
 
iseVolume27StatusDetailsStr    OBJECT-TYPE
        SYNTAX          DisplayString
        MAX-ACCESS      read-only
        STATUS          current
        DESCRIPTION
        "iseVolume27 Volume Current Status Details string - longer description when status is not Operational"
        ::= { iseVolume27 12 }    -- 1.3.6.1.4.1.2366.6.1.2.1.8.27.12.0
 
iseVolume27IsSnapshot    OBJECT-TYPE
        SYNTAX          DisplayString
        MAX-ACCESS      read-only
        STATUS          current
        DESCRIPTION
        "iseVolume27 Volume N Is a Snapshot?  value is unknown, yes, or no"
        ::= { iseVolume27 13 }    -- 1.3.6.1.4.1.2366.6.1.2.1.8.27.13.0
 
iseVolume27SnapshotChildId    OBJECT-TYPE
        SYNTAX          Integer32
        MAX-ACCESS      read-only
        STATUS          current
        DESCRIPTION
        "iseVolume27 Volumes Snapshot Child ID - value of 0 means NO Snapshot Child exists"
        ::= { iseVolume27 14 }    -- 1.3.6.1.4.1.2366.6.1.2.1.8.27.14.0
 
iseVolume27SnapshotParentId    OBJECT-TYPE
        SYNTAX          Integer32
        MAX-ACCESS      read-only
        STATUS          current
        DESCRIPTION
        "iseVolume27 Volumes Snapshot Parent ID - value of 0 means NO Snapshot Parent exists"
        ::= { iseVolume27 15 }    -- 1.3.6.1.4.1.2366.6.1.2.1.8.27.15.0
 
iseVolume28 OBJECT IDENTIFIER       ::= { iseStorageVols 28 }       -- 1.3.6.1.4.1.2366.6.1.2.1.8.28
 
iseVolume28Name    OBJECT-TYPE
        SYNTAX          DisplayString
        MAX-ACCESS      read-only
        STATUS          current
        DESCRIPTION
        "iseVolume28 Volume Name: ffx_xioB_13"
        ::= { iseVolume28 1 }    -- 1.3.6.1.4.1.2366.6.1.2.1.8.28.1.0
 
iseVolume28VpdId    OBJECT-TYPE
        SYNTAX          DisplayString
        MAX-ACCESS      read-only
        STATUS          current
        DESCRIPTION
        "iseVolume28 Volume VpdId: TBD"
        ::= { iseVolume28 2 }    -- 1.3.6.1.4.1.2366.6.1.2.1.8.28.2.0
 
iseVolume28DetailedStatus    OBJECT-TYPE
        SYNTAX          Integer32
        MAX-ACCESS      read-only
        STATUS          current
        DESCRIPTION
        "iseVolume28 Volume Detailed Status code"
        ::= { iseVolume28 3 }    -- 1.3.6.1.4.1.2366.6.1.2.1.8.28.3.0
 
iseVolume28Status    OBJECT-TYPE
        SYNTAX          Integer32
        MAX-ACCESS      read-only
        STATUS          current
        DESCRIPTION
        "iseVolume28 Volume Status"
        ::= { iseVolume28 4 }    -- 1.3.6.1.4.1.2366.6.1.2.1.8.28.4.0
 
iseVolume28Id    OBJECT-TYPE
        SYNTAX          Integer32
        MAX-ACCESS      read-only
        STATUS          current
        DESCRIPTION
        "iseVolume28 Volume Id"
        ::= { iseVolume28 5 }    -- 1.3.6.1.4.1.2366.6.1.2.1.8.28.5.0
 
iseVolume28RaidType    OBJECT-TYPE
        SYNTAX          Integer32
        MAX-ACCESS      read-only
        STATUS          current
        DESCRIPTION
        "iseVolume28 RaidType"
        ::= { iseVolume28 6 }    -- 1.3.6.1.4.1.2366.6.1.2.1.8.28.6.0
 
iseVolume28Pool    OBJECT-TYPE
        SYNTAX          Integer32
        MAX-ACCESS      read-only
        STATUS          current
        DESCRIPTION
        "iseVolume28 Storage Pool this volume was created from"
        ::= { iseVolume28 7 }    -- 1.3.6.1.4.1.2366.6.1.2.1.8.28.7.0
 
iseVolume28AllocationType    OBJECT-TYPE
        SYNTAX          Integer32
        MAX-ACCESS      read-only
        STATUS          current
        DESCRIPTION
        "iseVolume28 Allocation Type"
        ::= { iseVolume28 8 }    -- 1.3.6.1.4.1.2366.6.1.2.1.8.28.8.0
 
iseVolume28CacheType    OBJECT-TYPE
        SYNTAX          DisplayString
        MAX-ACCESS      read-only
        STATUS          current
        DESCRIPTION
        "iseVolume28 Volume Cache Type"
        ::= { iseVolume28 9 }    -- 1.3.6.1.4.1.2366.6.1.2.1.8.28.9.0
 
iseVolume28Size    OBJECT-TYPE
        SYNTAX          Integer32
        MAX-ACCESS      read-only
        STATUS          current
        DESCRIPTION
        "iseVolume28 Volume Size in GB"
        ::= { iseVolume28 10 }    -- 1.3.6.1.4.1.2366.6.1.2.1.8.28.10.0
 
iseVolume28StatusStr    OBJECT-TYPE
        SYNTAX          DisplayString
        MAX-ACCESS      read-only
        STATUS          current
        DESCRIPTION
        "iseVolume28 Current Status string - short description"
        ::= { iseVolume28 11 }    -- 1.3.6.1.4.1.2366.6.1.2.1.8.28.11.0
 
iseVolume28StatusDetailsStr    OBJECT-TYPE
        SYNTAX          DisplayString
        MAX-ACCESS      read-only
        STATUS          current
        DESCRIPTION
        "iseVolume28 Volume Current Status Details string - longer description when status is not Operational"
        ::= { iseVolume28 12 }    -- 1.3.6.1.4.1.2366.6.1.2.1.8.28.12.0
 
iseVolume28IsSnapshot    OBJECT-TYPE
        SYNTAX          DisplayString
        MAX-ACCESS      read-only
        STATUS          current
        DESCRIPTION
        "iseVolume28 Volume N Is a Snapshot?  value is unknown, yes, or no"
        ::= { iseVolume28 13 }    -- 1.3.6.1.4.1.2366.6.1.2.1.8.28.13.0
 
iseVolume28SnapshotChildId    OBJECT-TYPE
        SYNTAX          Integer32
        MAX-ACCESS      read-only
        STATUS          current
        DESCRIPTION
        "iseVolume28 Volumes Snapshot Child ID - value of 0 means NO Snapshot Child exists"
        ::= { iseVolume28 14 }    -- 1.3.6.1.4.1.2366.6.1.2.1.8.28.14.0
 
iseVolume28SnapshotParentId    OBJECT-TYPE
        SYNTAX          Integer32
        MAX-ACCESS      read-only
        STATUS          current
        DESCRIPTION
        "iseVolume28 Volumes Snapshot Parent ID - value of 0 means NO Snapshot Parent exists"
        ::= { iseVolume28 15 }    -- 1.3.6.1.4.1.2366.6.1.2.1.8.28.15.0
 
 
-- ** VOLUME DEFINITIONS END


-- ** HOST DEFINITIONS BEGIN
  

 
iseHost1 OBJECT IDENTIFIER       ::= { iseStorageHosts 1 }       -- 1.3.6.1.4.1.2366.6.1.2.1.9.1
 
iseHost1Name    OBJECT-TYPE
        SYNTAX          DisplayString
        MAX-ACCESS      read-only
        STATUS          current
        DESCRIPTION
        "iseHost1 Host Name "
        ::= { iseHost1 1 }    -- 1.3.6.1.4.1.2366.6.1.2.1.9.1.1.0
 
iseHost1Os    OBJECT-TYPE
        SYNTAX          DisplayString
        MAX-ACCESS      read-only
        STATUS          current
        DESCRIPTION
        "iseHost1 Host OS "
        ::= { iseHost1 2 }    -- 1.3.6.1.4.1.2366.6.1.2.1.9.1.2.0
 
iseHost1Id    OBJECT-TYPE
        SYNTAX          Integer32
        MAX-ACCESS      read-only
        STATUS          current
        DESCRIPTION
        "iseHost1 Host ID "
        ::= { iseHost1 3 }    -- 1.3.6.1.4.1.2366.6.1.2.1.9.1.3.0
 
iseHost1StatusStr    OBJECT-TYPE
        SYNTAX          DisplayString
        MAX-ACCESS      read-only
        STATUS          current
        DESCRIPTION
        "iseHost1 Host Status String - short description of Host State"
        ::= { iseHost1 4 }    -- 1.3.6.1.4.1.2366.6.1.2.1.9.1.4.0
 
iseHost1StatusDetailsStr    OBJECT-TYPE
        SYNTAX          DisplayString
        MAX-ACCESS      read-only
        STATUS          current
        DESCRIPTION
        "iseHost1 Host Status Details String - detailed description of Host State"
        ::= { iseHost1 5 }    -- 1.3.6.1.4.1.2366.6.1.2.1.9.1.5.0
 
iseHost2 OBJECT IDENTIFIER       ::= { iseStorageHosts 2 }       -- 1.3.6.1.4.1.2366.6.1.2.1.9.2
 
iseHost2Name    OBJECT-TYPE
        SYNTAX          DisplayString
        MAX-ACCESS      read-only
        STATUS          current
        DESCRIPTION
        "iseHost2 Host Name "
        ::= { iseHost2 1 }    -- 1.3.6.1.4.1.2366.6.1.2.1.9.2.1.0
 
iseHost2Os    OBJECT-TYPE
        SYNTAX          DisplayString
        MAX-ACCESS      read-only
        STATUS          current
        DESCRIPTION
        "iseHost2 Host OS "
        ::= { iseHost2 2 }    -- 1.3.6.1.4.1.2366.6.1.2.1.9.2.2.0
 
iseHost2Id    OBJECT-TYPE
        SYNTAX          Integer32
        MAX-ACCESS      read-only
        STATUS          current
        DESCRIPTION
        "iseHost2 Host ID "
        ::= { iseHost2 3 }    -- 1.3.6.1.4.1.2366.6.1.2.1.9.2.3.0
 
iseHost2StatusStr    OBJECT-TYPE
        SYNTAX          DisplayString
        MAX-ACCESS      read-only
        STATUS          current
        DESCRIPTION
        "iseHost2 Host Status String - short description of Host State"
        ::= { iseHost2 4 }    -- 1.3.6.1.4.1.2366.6.1.2.1.9.2.4.0
 
iseHost2StatusDetailsStr    OBJECT-TYPE
        SYNTAX          DisplayString
        MAX-ACCESS      read-only
        STATUS          current
        DESCRIPTION
        "iseHost2 Host Status Details String - detailed description of Host State"
        ::= { iseHost2 5 }    -- 1.3.6.1.4.1.2366.6.1.2.1.9.2.5.0
 
iseHost3 OBJECT IDENTIFIER       ::= { iseStorageHosts 3 }       -- 1.3.6.1.4.1.2366.6.1.2.1.9.3
 
iseHost3Name    OBJECT-TYPE
        SYNTAX          DisplayString
        MAX-ACCESS      read-only
        STATUS          current
        DESCRIPTION
        "iseHost3 Host Name "
        ::= { iseHost3 1 }    -- 1.3.6.1.4.1.2366.6.1.2.1.9.3.1.0
 
iseHost3Os    OBJECT-TYPE
        SYNTAX          DisplayString
        MAX-ACCESS      read-only
        STATUS          current
        DESCRIPTION
        "iseHost3 Host OS "
        ::= { iseHost3 2 }    -- 1.3.6.1.4.1.2366.6.1.2.1.9.3.2.0
 
iseHost3Id    OBJECT-TYPE
        SYNTAX          Integer32
        MAX-ACCESS      read-only
        STATUS          current
        DESCRIPTION
        "iseHost3 Host ID "
        ::= { iseHost3 3 }    -- 1.3.6.1.4.1.2366.6.1.2.1.9.3.3.0
 
iseHost3StatusStr    OBJECT-TYPE
        SYNTAX          DisplayString
        MAX-ACCESS      read-only
        STATUS          current
        DESCRIPTION
        "iseHost3 Host Status String - short description of Host State"
        ::= { iseHost3 4 }    -- 1.3.6.1.4.1.2366.6.1.2.1.9.3.4.0
 
iseHost3StatusDetailsStr    OBJECT-TYPE
        SYNTAX          DisplayString
        MAX-ACCESS      read-only
        STATUS          current
        DESCRIPTION
        "iseHost3 Host Status Details String - detailed description of Host State"
        ::= { iseHost3 5 }    -- 1.3.6.1.4.1.2366.6.1.2.1.9.3.5.0
 
iseHost4 OBJECT IDENTIFIER       ::= { iseStorageHosts 4 }       -- 1.3.6.1.4.1.2366.6.1.2.1.9.4
 
iseHost4Name    OBJECT-TYPE
        SYNTAX          DisplayString
        MAX-ACCESS      read-only
        STATUS          current
        DESCRIPTION
        "iseHost4 Host Name "
        ::= { iseHost4 1 }    -- 1.3.6.1.4.1.2366.6.1.2.1.9.4.1.0
 
iseHost4Os    OBJECT-TYPE
        SYNTAX          DisplayString
        MAX-ACCESS      read-only
        STATUS          current
        DESCRIPTION
        "iseHost4 Host OS "
        ::= { iseHost4 2 }    -- 1.3.6.1.4.1.2366.6.1.2.1.9.4.2.0
 
iseHost4Id    OBJECT-TYPE
        SYNTAX          Integer32
        MAX-ACCESS      read-only
        STATUS          current
        DESCRIPTION
        "iseHost4 Host ID "
        ::= { iseHost4 3 }    -- 1.3.6.1.4.1.2366.6.1.2.1.9.4.3.0
 
iseHost4StatusStr    OBJECT-TYPE
        SYNTAX          DisplayString
        MAX-ACCESS      read-only
        STATUS          current
        DESCRIPTION
        "iseHost4 Host Status String - short description of Host State"
        ::= { iseHost4 4 }    -- 1.3.6.1.4.1.2366.6.1.2.1.9.4.4.0
 
iseHost4StatusDetailsStr    OBJECT-TYPE
        SYNTAX          DisplayString
        MAX-ACCESS      read-only
        STATUS          current
        DESCRIPTION
        "iseHost4 Host Status Details String - detailed description of Host State"
        ::= { iseHost4 5 }    -- 1.3.6.1.4.1.2366.6.1.2.1.9.4.5.0
 
iseHost5 OBJECT IDENTIFIER       ::= { iseStorageHosts 5 }       -- 1.3.6.1.4.1.2366.6.1.2.1.9.5
 
iseHost5Name    OBJECT-TYPE
        SYNTAX          DisplayString
        MAX-ACCESS      read-only
        STATUS          current
        DESCRIPTION
        "iseHost5 Host Name "
        ::= { iseHost5 1 }    -- 1.3.6.1.4.1.2366.6.1.2.1.9.5.1.0
 
iseHost5Os    OBJECT-TYPE
        SYNTAX          DisplayString
        MAX-ACCESS      read-only
        STATUS          current
        DESCRIPTION
        "iseHost5 Host OS "
        ::= { iseHost5 2 }    -- 1.3.6.1.4.1.2366.6.1.2.1.9.5.2.0
 
iseHost5Id    OBJECT-TYPE
        SYNTAX          Integer32
        MAX-ACCESS      read-only
        STATUS          current
        DESCRIPTION
        "iseHost5 Host ID "
        ::= { iseHost5 3 }    -- 1.3.6.1.4.1.2366.6.1.2.1.9.5.3.0
 
iseHost5StatusStr    OBJECT-TYPE
        SYNTAX          DisplayString
        MAX-ACCESS      read-only
        STATUS          current
        DESCRIPTION
        "iseHost5 Host Status String - short description of Host State"
        ::= { iseHost5 4 }    -- 1.3.6.1.4.1.2366.6.1.2.1.9.5.4.0
 
iseHost5StatusDetailsStr    OBJECT-TYPE
        SYNTAX          DisplayString
        MAX-ACCESS      read-only
        STATUS          current
        DESCRIPTION
        "iseHost5 Host Status Details String - detailed description of Host State"
        ::= { iseHost5 5 }    -- 1.3.6.1.4.1.2366.6.1.2.1.9.5.5.0
 
 
-- ** HOST DEFINITIONS END

--*******************************************************************************************
--*******************************  Fibre Channel Ports  *************************************
--*******************************************************************************************

-- iseFcPorts     OBJECT IDENTIFIER	::= { iseObjects 10 }   - 1.3.6.1.4.1.2366.6.1.2.1.10
fcPort1 OBJECT IDENTIFIER	::= { iseFcPorts 1 } -- 1.3.6.1.4.1.2366.6.1.2.1.10.1

fcPort1WWN OBJECT-TYPE
	SYNTAX		DisplayString
	MAX-ACCESS	read-only
	STATUS 		current
	DESCRIPTION	
	 "Fibre Channel Port 1 WWN"
	::= { fcPort1 1 }    -- 1.3.6.1.4.1.2366.6.1.2.1.10.1.1	
	
fcPort1Status OBJECT-TYPE
	SYNTAX		Integer32
	MAX-ACCESS	read-only
	STATUS 		current
	DESCRIPTION	
	 "Fibre Channel Port 1 Status"
	::= { fcPort1 2 }    -- 1.3.6.1.4.1.2366.6.1.2.1.10.1.2
	
fcPort1StatusStr OBJECT-TYPE
	SYNTAX		DisplayString
	MAX-ACCESS	read-only
	STATUS 		current
	DESCRIPTION	
	 "Fibre Channel Port 1 Status String"
	::= { fcPort1 3 }    -- 1.3.6.1.4.1.2366.6.1.2.1.10.1.3	
	
fcPort1Type OBJECT-TYPE
	SYNTAX		Integer32
	MAX-ACCESS	read-only
	STATUS 		current
	DESCRIPTION	
	 "Fibre Channel Port 1 Type"
	::= { fcPort1 4 }    -- 1.3.6.1.4.1.2366.6.1.2.1.10.1.4
	
fcPort1Speed OBJECT-TYPE
	SYNTAX		Integer32
	MAX-ACCESS	read-only
	STATUS 		current
	DESCRIPTION	
	 "Fibre Channel Port 1 Speed"
	::= { fcPort1 5 }    -- 1.3.6.1.4.1.2366.6.1.2.1.10.1.5
			
	
--*********************************  FcPort 2  ***********************************

fcPort2 OBJECT IDENTIFIER	::= { iseFcPorts 2 } -- 1.3.6.1.4.1.2366.6.1.2.1.10.2

fcPort2WWN OBJECT-TYPE
	SYNTAX		DisplayString
	MAX-ACCESS	read-only
	STATUS 		current
	DESCRIPTION	
	 "Fibre Channel Port 2 WWN"
	::= { fcPort2 1 }    -- 1.3.6.1.4.1.2366.6.1.2.1.10.2.1	
	
fcPort2Status OBJECT-TYPE
	SYNTAX		Integer32
	MAX-ACCESS	read-only
	STATUS 		current
	DESCRIPTION	
	 "Fibre Channel Port 2 Status"
	::= { fcPort2 2 }    -- 1.3.6.1.4.1.2366.6.1.2.1.10.2.2
	
fcPort2StatusStr OBJECT-TYPE
	SYNTAX		DisplayString
	MAX-ACCESS	read-only
	STATUS 		current
	DESCRIPTION	
	 "Fibre Channel Port 2 Status String"
	::= { fcPort2 3 }    -- 1.3.6.1.4.1.2366.6.1.2.1.10.2.3	
	
fcPort2Type OBJECT-TYPE
	SYNTAX		Integer32
	MAX-ACCESS	read-only
	STATUS 		current
	DESCRIPTION	
	 "Fibre Channel Port 2 Type"
	::= { fcPort2 4 }    -- 1.3.6.1.4.1.2366.6.1.2.1.10.2.4
	
fcPort2Speed OBJECT-TYPE
	SYNTAX		Integer32
	MAX-ACCESS	read-only
	STATUS 		current
	DESCRIPTION	
	 "Fibre Channel Port 2 Speed"
	::= { fcPort2 5 }    -- 1.3.6.1.4.1.2366.6.1.2.1.10.2.5
				
--*********************************  FcPort 3  ***********************************

fcPort3 OBJECT IDENTIFIER	::= { iseFcPorts 3 } -- 1.3.6.1.4.1.2366.6.1.2.1.10.3

fcPort3WWN OBJECT-TYPE
	SYNTAX		DisplayString
	MAX-ACCESS	read-only
	STATUS 		current
	DESCRIPTION	
	 "Fibre Channel Port 3 WWN"
	::= { fcPort3 1 }    -- 1.3.6.1.4.1.2366.6.1.2.1.10.3.1	
	
fcPort3Status OBJECT-TYPE
	SYNTAX		Integer32
	MAX-ACCESS	read-only
	STATUS 		current
	DESCRIPTION	
	 "Fibre Channel Port 3 Status"
	::= { fcPort3 2 }    -- 1.3.6.1.4.1.2366.6.1.2.1.10.3.2
	
fcPort3StatusStr OBJECT-TYPE
	SYNTAX		DisplayString
	MAX-ACCESS	read-only
	STATUS 		current
	DESCRIPTION	
	 "Fibre Channel Port 3 Status String"
	::= { fcPort3 3 }    -- 1.3.6.1.4.1.2366.6.1.2.1.10.3.3	
	
fcPort3Type OBJECT-TYPE
	SYNTAX		Integer32
	MAX-ACCESS	read-only
	STATUS 		current
	DESCRIPTION	
	 "Fibre Channel Port 3 Type"
	::= { fcPort3 4 }    -- 1.3.6.1.4.1.2366.6.1.2.1.10.3.4
	
fcPort3Speed OBJECT-TYPE
	SYNTAX		Integer32
	MAX-ACCESS	read-only
	STATUS 		current
	DESCRIPTION	
	 "Fibre Channel Port 3 Speed"
	::= { fcPort3 5 }    -- 1.3.6.1.4.1.2366.6.1.2.1.10.3.5
	

--*********************************  FcPort 4  ***********************************

fcPort4 OBJECT IDENTIFIER	::= { iseFcPorts 4 } -- 1.3.6.1.4.1.2366.6.1.2.1.10.4

fcPort4WWN OBJECT-TYPE
	SYNTAX		DisplayString
	MAX-ACCESS	read-only
	STATUS 		current
	DESCRIPTION	
	 "Fibre Channel Port 4 WWN"
	::= { fcPort4 1 }    -- 1.3.6.1.4.1.2366.6.1.2.1.10.4.1	
	
fcPort4Status OBJECT-TYPE
	SYNTAX		Integer32
	MAX-ACCESS	read-only
	STATUS 		current
	DESCRIPTION	
	 "Fibre Channel Port 4 Status"
	::= { fcPort4 2 }    -- 1.3.6.1.4.1.2366.6.1.2.1.10.4.2
	
fcPort4StatusStr OBJECT-TYPE
	SYNTAX		DisplayString
	MAX-ACCESS	read-only
	STATUS 		current
	DESCRIPTION	
	 "Fibre Channel Port 4 Status String"
	::= { fcPort4 3 }    -- 1.3.6.1.4.1.2366.6.1.2.1.10.4.3	
	
fcPort4Type OBJECT-TYPE
	SYNTAX		Integer32
	MAX-ACCESS	read-only
	STATUS 		current
	DESCRIPTION	
	 "Fibre Channel Port 4 Type"
	::= { fcPort4 4 }    -- 1.3.6.1.4.1.2366.6.1.2.1.10.4.4
	
fcPort4Speed OBJECT-TYPE
	SYNTAX		Integer32
	MAX-ACCESS	read-only
	STATUS 		current
	DESCRIPTION	
	 "Fibre Channel Port 4 Speed"
	::= { fcPort4 5 }    -- 1.3.6.1.4.1.2366.6.1.2.1.10.4.5
	
--*********************************  FcPort 5  ***********************************

fcPort5 OBJECT IDENTIFIER	::= { iseFcPorts 5 } -- 1.3.6.1.4.1.2366.6.1.2.1.10.5

fcPort5WWN OBJECT-TYPE
	SYNTAX		DisplayString
	MAX-ACCESS	read-only
	STATUS 		current
	DESCRIPTION	
	 "Fibre Channel Port 5 WWN"
	::= { fcPort5 1 }    -- 1.3.6.1.4.1.2366.6.1.2.1.10.5.1	
	
fcPort5Status OBJECT-TYPE
	SYNTAX		Integer32
	MAX-ACCESS	read-only
	STATUS 		current
	DESCRIPTION	
	 "Fibre Channel Port 5 Status"
	::= { fcPort5 2 }    -- 1.3.6.1.4.1.2366.6.1.2.1.10.5.2
	
fcPort5StatusStr OBJECT-TYPE
	SYNTAX		DisplayString
	MAX-ACCESS	read-only
	STATUS 		current
	DESCRIPTION	
	 "Fibre Channel Port 5 Status String"
	::= { fcPort5 3 }    -- 1.3.6.1.4.1.2366.6.1.2.1.10.5.3	
	
fcPort5Type OBJECT-TYPE
	SYNTAX		Integer32
	MAX-ACCESS	read-only
	STATUS 		current
	DESCRIPTION	
	 "Fibre Channel Port 5 Type"
	::= { fcPort5 4 }    -- 1.3.6.1.4.1.2366.6.1.2.1.10.5.4
	
fcPort5Speed OBJECT-TYPE
	SYNTAX		Integer32
	MAX-ACCESS	read-only
	STATUS 		current
	DESCRIPTION	
	 "Fibre Channel Port 5 Speed"
	::= { fcPort5 5 }    -- 1.3.6.1.4.1.2366.6.1.2.1.10.5.5
	
--*********************************  FcPort 6  ***********************************

fcPort6 OBJECT IDENTIFIER	::= { iseFcPorts 6 } -- 1.3.6.1.4.1.2366.6.1.2.1.10.6

fcPort6WWN OBJECT-TYPE
	SYNTAX		DisplayString
	MAX-ACCESS	read-only
	STATUS 		current
	DESCRIPTION	
	 "Fibre Channel Port 6 WWN"
	::= { fcPort6 1 }    -- 1.3.6.1.4.1.2366.6.1.2.1.10.6.1	
	
fcPort6Status OBJECT-TYPE
	SYNTAX		Integer32
	MAX-ACCESS	read-only
	STATUS 		current
	DESCRIPTION	
	 "Fibre Channel Port 6 Status"
	::= { fcPort6 2 }    -- 1.3.6.1.4.1.2366.6.1.2.1.10.6.2
	
fcPort6StatusStr OBJECT-TYPE
	SYNTAX		DisplayString
	MAX-ACCESS	read-only
	STATUS 		current
	DESCRIPTION	
	 "Fibre Channel Port 6 Status String"
	::= { fcPort6 3 }    -- 1.3.6.1.4.1.2366.6.1.2.1.10.6.3	
	
fcPort6Type OBJECT-TYPE
	SYNTAX		Integer32
	MAX-ACCESS	read-only
	STATUS 		current
	DESCRIPTION	
	 "Fibre Channel Port 6 Type"
	::= { fcPort6 4 }    -- 1.3.6.1.4.1.2366.6.1.2.1.10.6.4
	
fcPort6Speed OBJECT-TYPE
	SYNTAX		Integer32
	MAX-ACCESS	read-only
	STATUS 		current
	DESCRIPTION	
	 "Fibre Channel Port 6 Speed"
	::= { fcPort6 5 }    -- 1.3.6.1.4.1.2366.6.1.2.1.10.6.5
	
--*********************************  FcPort 7  ***********************************

fcPort7 OBJECT IDENTIFIER	::= { iseFcPorts 7 } -- 1.3.6.1.4.1.2366.6.1.2.1.10.7

fcPort7WWN OBJECT-TYPE
	SYNTAX		DisplayString
	MAX-ACCESS	read-only
	STATUS 		current
	DESCRIPTION	
	 "Fibre Channel Port 7 WWN"
	::= { fcPort7 1 }    -- 1.3.6.1.4.1.2366.6.1.2.1.10.7.1	
	
fcPort7Status OBJECT-TYPE
	SYNTAX		Integer32
	MAX-ACCESS	read-only
	STATUS 		current
	DESCRIPTION	
	 "Fibre Channel Port 7 Status"
	::= { fcPort7 2 }    -- 1.3.6.1.4.1.2366.6.1.2.1.10.7.2
	
fcPort7StatusStr OBJECT-TYPE
	SYNTAX		DisplayString
	MAX-ACCESS	read-only
	STATUS 		current
	DESCRIPTION	
	 "Fibre Channel Port 7 Status String"
	::= { fcPort7 3 }    -- 1.3.6.1.4.1.2366.6.1.2.1.10.7.3	
	
fcPort7Type OBJECT-TYPE
	SYNTAX		Integer32
	MAX-ACCESS	read-only
	STATUS 		current
	DESCRIPTION	
	 "Fibre Channel Port 7 Type"
	::= { fcPort7 4 }    -- 1.3.6.1.4.1.2366.6.1.2.1.10.7.4
	
fcPort7Speed OBJECT-TYPE
	SYNTAX		Integer32
	MAX-ACCESS	read-only
	STATUS 		current
	DESCRIPTION	
	 "Fibre Channel Port 7 Speed"
	::= { fcPort7 5 }    -- 1.3.6.1.4.1.2366.6.1.2.1.10.7.5
	
--*********************************  FcPort 8  ***********************************

fcPort8 OBJECT IDENTIFIER	::= { iseFcPorts 8 } -- 1.3.6.1.4.1.2366.6.1.2.1.10.8

fcPort8WWN OBJECT-TYPE
	SYNTAX		DisplayString
	MAX-ACCESS	read-only
	STATUS 		current
	DESCRIPTION	
	 "Fibre Channel Port 8 WWN"
	::= { fcPort8 1 }    -- 1.3.6.1.4.1.2366.6.1.2.1.10.8.1	
	
fcPort8Status OBJECT-TYPE
	SYNTAX		Integer32
	MAX-ACCESS	read-only
	STATUS 		current
	DESCRIPTION	
	 "Fibre Channel Port 8 Status"
	::= { fcPort8 2 }    -- 1.3.6.1.4.1.2366.6.1.2.1.10.8.2
	
fcPort8StatusStr OBJECT-TYPE
	SYNTAX		DisplayString
	MAX-ACCESS	read-only
	STATUS 		current
	DESCRIPTION	
	 "Fibre Channel Port 8 Status String"
	::= { fcPort8 3 }    -- 1.3.6.1.4.1.2366.6.1.2.1.10.8.3	
	
fcPort8Type OBJECT-TYPE
	SYNTAX		Integer32
	MAX-ACCESS	read-only
	STATUS 		current
	DESCRIPTION	
	 "Fibre Channel Port 8 Type"
	::= { fcPort8 4 }    -- 1.3.6.1.4.1.2366.6.1.2.1.10.8.4
	
fcPort8Speed OBJECT-TYPE
	SYNTAX		Integer32
	MAX-ACCESS	read-only
	STATUS 		current
	DESCRIPTION	
	 "Fibre Channel Port 8 Speed"
	::= { fcPort8 5 }    -- 1.3.6.1.4.1.2366.6.1.2.1.10.8.5
		

--*******************************************************************************************
--*******************************  SFPs  *************************************
--*******************************************************************************************

-- iseSfps     OBJECT IDENTIFIER	::= { iseObjects 11 }   - 1.3.6.1.4.1.2366.6.1.2.1.11

--*********************************  Sfp 1  ***********************************

sfp1 OBJECT IDENTIFIER	::= { iseSfps 1 } -- 1.3.6.1.4.1.2366.6.1.2.1.11.1

sfp1Id OBJECT-TYPE
	SYNTAX		Integer32
	MAX-ACCESS	read-only
	STATUS 		current
	DESCRIPTION	
	 "SFP 1 ID"
	::= { sfp1 1 }    -- 1.3.6.1.4.1.2366.6.1.2.1.11.1.1	
	
sfp1IsPresent OBJECT-TYPE
	SYNTAX		DisplayString
	MAX-ACCESS	read-only
	STATUS 		current
	DESCRIPTION	
	 "SFP 1 is present?"
	::= { sfp1 2 }    -- 1.3.6.1.4.1.2366.6.1.2.1.11.1.2	
	
sfp1Status OBJECT-TYPE
	SYNTAX		Integer32
	MAX-ACCESS	read-only
	STATUS 		current
	DESCRIPTION	
	 "SFP 1 Status"
	::= { sfp1 3 }    -- 1.3.6.1.4.1.2366.6.1.2.1.11.1.3
	
sfp1StatusStr OBJECT-TYPE
	SYNTAX		DisplayString
	MAX-ACCESS	read-only
	STATUS 		current
	DESCRIPTION	
	 "SFP 1 Status String"
	::= { sfp1 4 }    -- 1.3.6.1.4.1.2366.6.1.2.1.11.1.4	
	
sfp1HardwareVersion OBJECT-TYPE
	SYNTAX		DisplayString
	MAX-ACCESS	read-only
	STATUS 		current
	DESCRIPTION	
	 "SFP 1 Hardware Version"
	::= { sfp1 5 }    -- 1.3.6.1.4.1.2366.6.1.2.1.11.1.5
	
sfp1SerialNum OBJECT-TYPE
	SYNTAX		DisplayString
	MAX-ACCESS	read-only
	STATUS 		current
	DESCRIPTION	
	 "SFP 1 Serial Number"
	::= { sfp1 6 }    -- 1.3.6.1.4.1.2366.6.1.2.1.11.1.6
		
sfp1PartNum OBJECT-TYPE
	SYNTAX		DisplayString
	MAX-ACCESS	read-only
	STATUS 		current
	DESCRIPTION	
	 "SFP 1 Part Number"
	::= { sfp1 7 }    -- 1.3.6.1.4.1.2366.6.1.2.1.11.1.7					
				
	
--*********************************  Sfp 2  ***********************************

sfp2 OBJECT IDENTIFIER	::= { iseSfps 2 } -- 1.3.6.1.4.1.2366.6.1.2.1.11.1

sfp2Id OBJECT-TYPE
	SYNTAX		Integer32
	MAX-ACCESS	read-only
	STATUS 		current
	DESCRIPTION	
	 "SFP 2 Id"
	::= { sfp2 1 }    -- 1.3.6.1.4.1.2366.6.1.2.1.11.2.1	
	
sfp2IsPresent OBJECT-TYPE
	SYNTAX		DisplayString
	MAX-ACCESS	read-only
	STATUS 		current
	DESCRIPTION	
	 "SFP 2 is present?"
	::= { sfp2 2 }    -- 1.3.6.1.4.1.2366.6.1.2.1.11.2.2	
	
sfp2Status OBJECT-TYPE
	SYNTAX		Integer32
	MAX-ACCESS	read-only
	STATUS 		current
	DESCRIPTION	
	 "SFP 2 Status"
	::= { sfp2 3 }    -- 1.3.6.1.4.1.2366.6.1.2.1.11.2.3
	
sfp2StatusStr OBJECT-TYPE
	SYNTAX		DisplayString
	MAX-ACCESS	read-only
	STATUS 		current
	DESCRIPTION	
	 "SFP 2 Status String"
	::= { sfp2 4 }    -- 1.3.6.1.4.1.2366.6.1.2.1.11.2.4	
	
sfp2HardwareVersion OBJECT-TYPE
	SYNTAX		DisplayString
	MAX-ACCESS	read-only
	STATUS 		current
	DESCRIPTION	
	 "SFP 2 Hardware Version"
	::= { sfp2 5 }    -- 1.3.6.1.4.1.2366.6.1.2.1.11.2.5
	
sfp2SerialNum OBJECT-TYPE
	SYNTAX		DisplayString
	MAX-ACCESS	read-only
	STATUS 		current
	DESCRIPTION	
	 "SFP 2 Serial Number"
	::= { sfp2 6 }    -- 1.3.6.1.4.1.2366.6.1.2.1.11.2.6
		
sfp2PartNum OBJECT-TYPE
	SYNTAX		DisplayString
	MAX-ACCESS	read-only
	STATUS 		current
	DESCRIPTION	
	 "SFP 2 Part Number"
	::= { sfp2 7 }    -- 1.3.6.1.4.1.2366.6.1.2.1.11.2.7	
		
	
--*********************************  Sfp 3  ***********************************

sfp3 OBJECT IDENTIFIER	::= { iseSfps 3 } -- 1.3.6.1.4.1.2366.6.1.2.1.11.1

sfp3Id OBJECT-TYPE
	SYNTAX		Integer32
	MAX-ACCESS	read-only
	STATUS 		current
	DESCRIPTION	
	 "SFP 3 Id"
	::= { sfp3 1 }    -- 1.3.6.1.4.1.2366.6.1.2.1.11.3.1	
	
sfp3IsPresent OBJECT-TYPE
	SYNTAX		DisplayString
	MAX-ACCESS	read-only
	STATUS 		current
	DESCRIPTION	
	 "SFP 3 is present?"
	::= { sfp3 2 }    -- 1.3.6.1.4.1.2366.6.1.2.1.11.3.2	
	
sfp3Status OBJECT-TYPE
	SYNTAX		Integer32
	MAX-ACCESS	read-only
	STATUS 		current
	DESCRIPTION	
	 "SFP 3 Status"
	::= { sfp3 3 }    -- 1.3.6.1.4.1.2366.6.1.2.1.11.3.3
	
sfp3StatusStr OBJECT-TYPE
	SYNTAX		DisplayString
	MAX-ACCESS	read-only
	STATUS 		current
	DESCRIPTION	
	 "SFP 3 Status String"
	::= { sfp3 4 }    -- 1.3.6.1.4.1.2366.6.1.2.1.11.3.4	
	
sfp3HardwareVersion OBJECT-TYPE
	SYNTAX		DisplayString
	MAX-ACCESS	read-only
	STATUS 		current
	DESCRIPTION	
	 "SFP 3 Hardware Version"
	::= { sfp3 5 }    -- 1.3.6.1.4.1.2366.6.1.2.1.11.3.5
	
sfp3SerialNum OBJECT-TYPE
	SYNTAX		DisplayString
	MAX-ACCESS	read-only
	STATUS 		current
	DESCRIPTION	
	 "SFP 3 Serial Number"
	::= { sfp3 6 }    -- 1.3.6.1.4.1.2366.6.1.2.1.11.3.6
		
sfp3PartNum OBJECT-TYPE
	SYNTAX		DisplayString
	MAX-ACCESS	read-only
	STATUS 		current
	DESCRIPTION	
	 "SFP 3 Part Number"
	::= { sfp3 7 }    -- 1.3.6.1.4.1.2366.6.1.2.1.11.3.7	
			
--*********************************  Sfp 4  ***********************************

sfp4 OBJECT IDENTIFIER	::= { iseSfps 4 } -- 1.3.6.1.4.1.2366.6.1.2.1.11.1

sfp4Id OBJECT-TYPE
	SYNTAX		Integer32
	MAX-ACCESS	read-only
	STATUS 		current
	DESCRIPTION	
	 "SFP 4 Id"
	::= { sfp4 1 }    -- 1.3.6.1.4.1.2366.6.1.2.1.11.4.1	
	
sfp4IsPresent OBJECT-TYPE
	SYNTAX		DisplayString
	MAX-ACCESS	read-only
	STATUS 		current
	DESCRIPTION	
	 "SFP 4 is present?"
	::= { sfp4 2 }    -- 1.3.6.1.4.1.2366.6.1.2.1.11.4.2	
	
sfp4Status OBJECT-TYPE
	SYNTAX		Integer32
	MAX-ACCESS	read-only
	STATUS 		current
	DESCRIPTION	
	 "SFP 4 Status"
	::= { sfp4 3 }    -- 1.3.6.1.4.1.2366.6.1.2.1.11.4.3
	
sfp4StatusStr OBJECT-TYPE
	SYNTAX		DisplayString
	MAX-ACCESS	read-only
	STATUS 		current
	DESCRIPTION	
	 "SFP 4 Status String"
	::= { sfp4 4 }    -- 1.3.6.1.4.1.2366.6.1.2.1.11.4.4	
	
sfp4HardwareVersion OBJECT-TYPE
	SYNTAX		DisplayString
	MAX-ACCESS	read-only
	STATUS 		current
	DESCRIPTION	
	 "SFP 4 Hardware Version"
	::= { sfp4 5 }    -- 1.3.6.1.4.1.2366.6.1.2.1.11.4.5
	
sfp4SerialNum OBJECT-TYPE
	SYNTAX		DisplayString
	MAX-ACCESS	read-only
	STATUS 		current
	DESCRIPTION	
	 "SFP 4 Serial Number"
	::= { sfp4 6 }    -- 1.3.6.1.4.1.2366.6.1.2.1.11.4.6
		
sfp4PartNum OBJECT-TYPE
	SYNTAX		DisplayString
	MAX-ACCESS	read-only
	STATUS 		current
	DESCRIPTION	
	 "SFP 4 Part Number"
	::= { sfp4 7 }    -- 1.3.6.1.4.1.2366.6.1.2.1.11.4.7	
			
--*********************************  Sfp 5  ***********************************

sfp5 OBJECT IDENTIFIER	::= { iseSfps 5 } -- 1.3.6.1.4.1.2366.6.1.2.1.11.1

sfp5Id OBJECT-TYPE
	SYNTAX		Integer32
	MAX-ACCESS	read-only
	STATUS 		current
	DESCRIPTION	
	 "SFP 5 Id"
	::= { sfp5 1 }    -- 1.3.6.1.4.1.2366.6.1.2.1.11.5.1	
	
sfp5IsPresent OBJECT-TYPE
	SYNTAX		DisplayString
	MAX-ACCESS	read-only
	STATUS 		current
	DESCRIPTION	
	 "SFP 5 is present?"
	::= { sfp5 2 }    -- 1.3.6.1.4.1.2366.6.1.2.1.11.5.2	
	
sfp5Status OBJECT-TYPE
	SYNTAX		Integer32
	MAX-ACCESS	read-only
	STATUS 		current
	DESCRIPTION	
	 "SFP 5 Status"
	::= { sfp5 3 }    -- 1.3.6.1.4.1.2366.6.1.2.1.11.5.3
	
sfp5StatusStr OBJECT-TYPE
	SYNTAX		DisplayString
	MAX-ACCESS	read-only
	STATUS 		current
	DESCRIPTION	
	 "SFP 5 Status String"
	::= { sfp5 4 }    -- 1.3.6.1.4.1.2366.6.1.2.1.11.5.4	
	
sfp5HardwareVersion OBJECT-TYPE
	SYNTAX		DisplayString
	MAX-ACCESS	read-only
	STATUS 		current
	DESCRIPTION	
	 "SFP 5 Hardware Version"
	::= { sfp5 5 }    -- 1.3.6.1.4.1.2366.6.1.2.1.11.5.5
	
sfp5SerialNum OBJECT-TYPE
	SYNTAX		DisplayString
	MAX-ACCESS	read-only
	STATUS 		current
	DESCRIPTION	
	 "SFP 5 Serial Number"
	::= { sfp5 6 }    -- 1.3.6.1.4.1.2366.6.1.2.1.11.5.6
		
sfp5PartNum OBJECT-TYPE
	SYNTAX		DisplayString
	MAX-ACCESS	read-only
	STATUS 		current
	DESCRIPTION	
	 "SFP 5 Part Number"
	::= { sfp5 7 }    -- 1.3.6.1.4.1.2366.6.1.2.1.11.5.7	
			
--*********************************  Sfp 6  ***********************************

sfp6 OBJECT IDENTIFIER	::= { iseSfps 6 } -- 1.3.6.1.4.1.2366.6.1.2.1.11.1

sfp6Id OBJECT-TYPE
	SYNTAX		Integer32
	MAX-ACCESS	read-only
	STATUS 		current
	DESCRIPTION	
	 "SFP 6 Id"
	::= { sfp6 1 }    -- 1.3.6.1.4.1.2366.6.1.2.1.11.6.1	
	
sfp6IsPresent OBJECT-TYPE
	SYNTAX		DisplayString
	MAX-ACCESS	read-only
	STATUS 		current
	DESCRIPTION	
	 "SFP 6 is present?"
	::= { sfp6 2 }    -- 1.3.6.1.4.1.2366.6.1.2.1.11.6.2	
	
sfp6Status OBJECT-TYPE
	SYNTAX		Integer32
	MAX-ACCESS	read-only
	STATUS 		current
	DESCRIPTION	
	 "SFP 6 Status"
	::= { sfp6 3 }    -- 1.3.6.1.4.1.2366.6.1.2.1.11.6.3
	
sfp6StatusStr OBJECT-TYPE
	SYNTAX		DisplayString
	MAX-ACCESS	read-only
	STATUS 		current
	DESCRIPTION	
	 "SFP 6 Status String"
	::= { sfp6 4 }    -- 1.3.6.1.4.1.2366.6.1.2.1.11.6.4	
	
sfp6HardwareVersion OBJECT-TYPE
	SYNTAX		DisplayString
	MAX-ACCESS	read-only
	STATUS 		current
	DESCRIPTION	
	 "SFP 6 Hardware Version"
	::= { sfp6 5 }    -- 1.3.6.1.4.1.2366.6.1.2.1.11.6.5
	
sfp6SerialNum OBJECT-TYPE
	SYNTAX		DisplayString
	MAX-ACCESS	read-only
	STATUS 		current
	DESCRIPTION	
	 "SFP 6 Serial Number"
	::= { sfp6 6 }    -- 1.3.6.1.4.1.2366.6.1.2.1.11.6.6
		
sfp6PartNum OBJECT-TYPE
	SYNTAX		DisplayString
	MAX-ACCESS	read-only
	STATUS 		current
	DESCRIPTION	
	 "SFP 6 Part Number"
	::= { sfp6 7 }    -- 1.3.6.1.4.1.2366.6.1.2.1.11.6.7	
			
--*********************************  Sfp 7  ***********************************

sfp7 OBJECT IDENTIFIER	::= { iseSfps 7 } -- 1.3.6.1.4.1.2366.6.1.2.1.11.1

sfp7Id OBJECT-TYPE
	SYNTAX		Integer32
	MAX-ACCESS	read-only
	STATUS 		current
	DESCRIPTION	
	 "SFP 7 Id"
	::= { sfp7 1 }    -- 1.3.6.1.4.1.2366.6.1.2.1.11.7.1	
	
sfp7IsPresent OBJECT-TYPE
	SYNTAX		DisplayString
	MAX-ACCESS	read-only
	STATUS 		current
	DESCRIPTION	
	 "SFP 7 is present?"
	::= { sfp7 2 }    -- 1.3.6.1.4.1.2366.6.1.2.1.11.7.2	
	
sfp7Status OBJECT-TYPE
	SYNTAX		Integer32
	MAX-ACCESS	read-only
	STATUS 		current
	DESCRIPTION	
	 "SFP 7 Status"
	::= { sfp7 3 }    -- 1.3.6.1.4.1.2366.6.1.2.1.11.7.3
	
sfp7StatusStr OBJECT-TYPE
	SYNTAX		DisplayString
	MAX-ACCESS	read-only
	STATUS 		current
	DESCRIPTION	
	 "SFP 7 Status String"
	::= { sfp7 4 }    -- 1.3.6.1.4.1.2366.6.1.2.1.11.7.4	
	
sfp7HardwareVersion OBJECT-TYPE
	SYNTAX		DisplayString
	MAX-ACCESS	read-only
	STATUS 		current
	DESCRIPTION	
	 "SFP 7 Hardware Version"
	::= { sfp7 5 }    -- 1.3.6.1.4.1.2366.6.1.2.1.11.7.5
	
sfp7SerialNum OBJECT-TYPE
	SYNTAX		DisplayString
	MAX-ACCESS	read-only
	STATUS 		current
	DESCRIPTION	
	 "SFP 7 Serial Number"
	::= { sfp7 6 }    -- 1.3.6.1.4.1.2366.6.1.2.1.11.7.6
		
sfp7PartNum OBJECT-TYPE
	SYNTAX		DisplayString
	MAX-ACCESS	read-only
	STATUS 		current
	DESCRIPTION	
	 "SFP 7 Part Number"
	::= { sfp7 7 }    -- 1.3.6.1.4.1.2366.6.1.2.1.11.7.7	
			
--*********************************  Sfp 8  ***********************************

sfp8 OBJECT IDENTIFIER	::= { iseSfps 8 } -- 1.3.6.1.4.1.2366.6.1.2.1.11.1

sfp8Id OBJECT-TYPE
	SYNTAX		Integer32
	MAX-ACCESS	read-only
	STATUS 		current
	DESCRIPTION	
	 "Sfp 8 Id"
	::= { sfp8 1 }    -- 1.3.6.1.4.1.2366.6.1.2.1.11.8.1	
	
sfp8IsPresent OBJECT-TYPE
	SYNTAX		DisplayString
	MAX-ACCESS	read-only
	STATUS 		current
	DESCRIPTION	
	 "SFP 8 is present?"
	::= { sfp8 2 }    -- 1.3.6.1.4.1.2366.6.1.2.1.11.8.2	
	
sfp8Status OBJECT-TYPE
	SYNTAX		Integer32
	MAX-ACCESS	read-only
	STATUS 		current
	DESCRIPTION	
	 "SFP 8 Status"
	::= { sfp8 3 }    -- 1.3.6.1.4.1.2366.6.1.2.1.11.8.3
	
sfp8StatusStr OBJECT-TYPE
	SYNTAX		DisplayString
	MAX-ACCESS	read-only
	STATUS 		current
	DESCRIPTION	
	 "SFP 8 Status String"
	::= { sfp8 4 }    -- 1.3.6.1.4.1.2366.6.1.2.1.11.8.4	
	
sfp8HardwareVersion OBJECT-TYPE
	SYNTAX		DisplayString
	MAX-ACCESS	read-only
	STATUS 		current
	DESCRIPTION	
	 "SFP 8 Hardware Version"
	::= { sfp8 5 }    -- 1.3.6.1.4.1.2366.6.1.2.1.11.8.5
	
sfp8SerialNum OBJECT-TYPE
	SYNTAX		DisplayString
	MAX-ACCESS	read-only
	STATUS 		current
	DESCRIPTION	
	 "SFP 8 Serial Number"
	::= { sfp8 6 }    -- 1.3.6.1.4.1.2366.6.1.2.1.11.8.6
		
sfp8PartNum OBJECT-TYPE
	SYNTAX		DisplayString
	MAX-ACCESS	read-only
	STATUS 		current
	DESCRIPTION	
	 "SFP 8 Part Number"
	::= { sfp8 7 }    -- 1.3.6.1.4.1.2366.6.1.2.1.11.8.7	
				
--********************************************************************		
--
-- Conformance Information

-- iseConformance   OBJECT IDENTIFIER	::= { iseStorage2 4 } - 1.3.6.1.4.1.2366.6.1.2.4

iseMIBGroups        OBJECT IDENTIFIER	::= { iseConformance 1 }  -- 1.3.6.1.4.1.2366.6.1.2.4.1
iseMIBCompliances   OBJECT IDENTIFIER	::= { iseConformance 2 }  -- 1.3.6.1.4.1.2366.6.1.2.4.2


-- Compliance statements

iseMIBCompliance    MODULE-COMPLIANCE
	STATUS			current
	DESCRIPTION     "The compliance statement for ISE entities which implement the ISE MIB."
	MODULE          -- this module
	MANDATORY-GROUPS { iseGroup, mrcGroup, dataPacGroup, asaStoragePoolGroup,
                         powerSupplyGroup, superCapGroup, volumeGroup, hostGroup, fcPortGroup, sfpGroup }
	::= { iseMIBCompliances 1 }             -- 1.3.6.1.4.1.2366.6.1.2.4.2.1

--iseAgentGroup		OBJECT-GROUP
--   OBJECTS {
--           }

iseGroup       OBJECT-GROUP
   OBJECTS {
             iseSerialNum,
             iseModel,
             iseVendor,
             iseManufacturer,
		     iseProductVersion,
             iseWWN,
             iseName,
             iseStatus,
             iseStatusDetails,
					   isePhysicalLocation,
					   iseAddress,
					   iseAdminName,
					   iseAdminPhone,
					   iseAdminEmail,
					   iseSpareLevel,
					   iseIpAddress1,
					   iseIpAddress2,
					   iseSubnetMask1,
					   iseSubnetMask2,
					   iseGateway1,
					   iseGateway2,
					   iseHostName1,
					   iseHostName2,
					   iseNetworkSpeed1,
					   iseNetworkSpeed2,
					   iseLinkUp,
					   iseFullDuplex,
					   iseDHCPEnabled,
					   iseWOLEnabled,
					   iseTemperature,
					   iseTotalVolumes,
					   iseTotalHosts,
					   iseStatusStr,
					   iseStatusDetailsStr
			}
    STATUS       current
    DESCRIPTION "A collection of ISE attribute objects"
    ::= { iseMIBGroups 1 }                                      -- 1.3.6.1.4.1.2366.6.1.2.4.1.1

mrcGroup  OBJECT-GROUP
   OBJECTS  {
				      mrc1Enabled,
				      mrc1Master,
				      mrc1Position,
				      mrc1Status,
                      mrc1StatusDetails,
				      mrc1PartNum,
				      mrc1SerialNum,
				      mrc1FirmwareVersion,
				      mrc1HardwareVersion,
				      mrc1Temperature,
				      mrc1TempThreshWarn,
				      mrc1TempThreshCrit,
				      mrc1FcStatus,
				      mrc1FcType,
				      mrc1FcPortWWN,
				      mrc1FcSpeed,
				      mrc1StatusStr,
				      mrc1StatusDetailsStr,
				      mrc1FcPortTypeStr,
                      mrc1SfpIsPresent,
                      mrc1SfpStatus,
                      mrc1FspStatusStr,
                      mrc1SfpHardwareVersion,
                      mrc1SfpSerialNum,
                      mrc1SfpPartNum,
		      
--
				      mrc2Enabled,
				      mrc2Master,
				      mrc2Position,
				      mrc2Status,
                      mrc2StatusDetails,
				      mrc2PartNum,
				      mrc2SerialNum,
				      mrc2FirmwareVersion,
				      mrc2HardwareVersion,
				      mrc2Temperature,
				      mrc2TempThreshWarn,
				      mrc2TempThreshCrit,
				      mrc2FcStatus,
				      mrc2FcType,
				      mrc2FcPortWWN,
				      mrc2FcSpeed,
				      mrc2StatusStr,
				      mrc2StatusDetailsStr,
				      mrc2FcPortTypeStr,
                      mrc2SfpIsPresent,
                      mrc2SfpStatus,
                      mrc2FspStatusStr,
                      mrc2SfpHardwareVersion,
                      mrc2SfpSerialNum,
                      mrc2SfpPartNum			      
			      }
    STATUS       current
    DESCRIPTION "A collection of MRC attribute objects"
    ::= { iseMIBGroups 2 }                                      -- 1.3.6.1.4.1.2366.6.1.2.4.1.2 

dataPacGroup         OBJECT-GROUP
   OBJECTS {        
            dataPac1PartNum,
            dataPac1Type,
            dataPac1Status,
            dataPac1StatusDetails,
            dataPac1SerialNum,
					  dataPac1FwVersion,
					  dataPac1Capacity,
					  dataPac1SpareLevel,
					  dataPac1Temperature,
					  dataPac1TempThreshWarn,
					  dataPac1TempThreshCrit,
					  dataPac1Health,
					  dataPac1NumDrives,
					  dataPac1NumBadDrives,
					  dataPac1StatusStr,
					  dataPac1StatusDetailsStr,
					  dataPac1Position,	
--					  				  
            dataPac2PartNum,
            dataPac2Type,
            dataPac2Status,
            dataPac2StatusDetails,
            dataPac2SerialNum,
					  dataPac2FwVersion,
					  dataPac2Capacity,
					  dataPac2SpareLevel,
					  dataPac2Temperature,
					  dataPac2TempThreshWarn,
					  dataPac2TempThreshCrit,
					  dataPac2Health,
					  dataPac2NumDrives,
					  dataPac2NumBadDrives,
					  dataPac2StatusStr,
					  dataPac2StatusDetailsStr,
					  dataPac2Position
			}
    STATUS       current
    DESCRIPTION "A collection of DataPac attribute objects"
    ::= { iseMIBGroups 3 }                                      -- 1.3.6.1.4.1.2366.6.1.2.4.1.3

asaStoragePoolGroup OBJECT-GROUP
   OBJECTS {
              storagePool1Id,
					    storagePool1DataPacUsage,
					    storagePool1Status,
					    storagePool1TotalAvailableSpace,
					    storagePool1TotalManagedSpace,
					    storagePool1MaxSizeRaid0,
					    storagePool1MaxSizeRaid1,
					    storagePool1MaxSizeRaid5,
					    storagePool1TotalVolumes,
					    storagePool1StatusStr,
					    storagePool1StatusDetailsStr,
						storagePool1UUIDStr,
	--				    
              storagePool2Id,
					    storagePool2DataPacUsage,
					    storagePool2Status,
					    storagePool2TotalAvailableSpace,
					    storagePool2TotalManagedSpace,
					    storagePool2MaxSizeRaid0,
					    storagePool2MaxSizeRaid1,
					    storagePool2MaxSizeRaid5,
					    storagePool2TotalVolumes,
					    storagePool2StatusStr,
					    storagePool2StatusDetailsStr,					    
						storagePool2UUIDStr
			}
    STATUS       current
    DESCRIPTION "A collection of StoragePool attribute objects"
    ::= { iseMIBGroups 4 }                                      -- 1.3.6.1.4.1.2366.6.1.2.4.1.4

powerSupplyGroup OBJECT-GROUP
   OBJECTS {
                        powerSupply1SerialNum,
					    powerSupply1PartNum,
					    powerSupply1Status,
					    powerSupply1StatusDetails,
					    powerSupply1Temperature,
					    powerSupply1TempThreshWarn,
					    powerSupply1TempThreshCrit,
					    powerSupply1Position,
					    powerSupply1FanStatus,
					    powerSupply1FanSpeed,
					    powerSupply1FanDesiredSpeed,
					    powerSupply1StatusStr,
					    powerSupply1StatusDetailsStr,
					    powerSupply1FanStatusStr,
					    powerSupply1Fan2Status,
					    powerSupply1Fan2Speed,
					    powerSupply1Fan2DesiredSpeed,
					    powerSupply1Fan2StatusStr,					    
--
                        powerSupply2SerialNum,
					    powerSupply2PartNum,
					    powerSupply2Status,
					    powerSupply2StatusDetails,
					    powerSupply2Temperature,
					    powerSupply2TempThreshWarn,
					    powerSupply2TempThreshCrit,
					    powerSupply2Position,
					    powerSupply2FanStatus,
					    powerSupply2FanSpeed,
					    powerSupply2FanDesiredSpeed,
					    powerSupply2StatusStr,
					    powerSupply2StatusDetailsStr,
					    powerSupply2FanStatusStr,
					    powerSupply2Fan2Status,
					    powerSupply2Fan2Speed,
					    powerSupply2Fan2DesiredSpeed,
					    powerSupply2Fan2StatusStr					    
		   }
    STATUS       current
    DESCRIPTION "A collection of Power Supply attribute objects"
    ::= { iseMIBGroups 5 }                                      -- 1.3.6.1.4.1.2366.6.1.2.4.1.5

superCapGroup OBJECT-GROUP
   OBJECTS {
              superCap1SerialNum,
			  superCap1PartNum,					    
			  superCap1HardwareVersion,
			  superCap1Status,
              superCap1StatusDetails,
              superCap1Temp,
              superCap1TempThreshWarn,
              superCap1TempThreshCrit,
              superCap1Position,
              superCap1StatusStr,
              superCap1StatusDetailsStr,
              superCap1Voltage,
--
              superCap2SerialNum,
			  superCap2PartNum,					    
			  superCap2HardwareVersion,
			  superCap2Status,
              superCap2StatusDetails,
              superCap2Temp,
              superCap2TempThreshWarn,
              superCap2TempThreshCrit,
              superCap2Position,
              superCap2StatusStr,
              superCap2StatusDetailsStr,
              superCap2Voltage
		   }
    STATUS       current
    DESCRIPTION "A collection of SuperCap attribute objects"
    ::= { iseMIBGroups 6 }                                      -- 1.3.6.1.4.1.2366.6.1.2.4.1.6
    
    
volumeGroup OBJECT-GROUP
   OBJECTS {
-- ** VOLUME GROUP DEFINITIONS BEGIN
 

 
              iseVolume16Name,
              iseVolume16VpdId,
              iseVolume16State,
              iseVolume16Status,
              iseVolume16Id,
              iseVolume16RaidType,
              iseVolume16Pool,
              iseVolume16AllocationType,
              iseVolume16CacheType,
              iseVolume16Size,
              iseVolume16StatusStr,
              iseVolume16StatusDetailsStr,
              iseVolume16IsSnapshot,
              iseVolume16SnapshotChildId,
              iseVolume16SnapshotParentId,
--
              iseVolume17Name,
              iseVolume17VpdId,
              iseVolume17State,
              iseVolume17Status,
              iseVolume17Id,
              iseVolume17RaidType,
              iseVolume17Pool,
              iseVolume17AllocationType,
              iseVolume17CacheType,
              iseVolume17Size,
              iseVolume17StatusStr,
              iseVolume17StatusDetailsStr,
              iseVolume17IsSnapshot,
              iseVolume17SnapshotChildId,
              iseVolume17SnapshotParentId,
--
              iseVolume18Name,
              iseVolume18VpdId,
              iseVolume18State,
              iseVolume18Status,
              iseVolume18Id,
              iseVolume18RaidType,
              iseVolume18Pool,
              iseVolume18AllocationType,
              iseVolume18CacheType,
              iseVolume18Size,
              iseVolume18StatusStr,
              iseVolume18StatusDetailsStr,
              iseVolume18IsSnapshot,
              iseVolume18SnapshotChildId,
              iseVolume18SnapshotParentId,
--
              iseVolume19Name,
              iseVolume19VpdId,
              iseVolume19State,
              iseVolume19Status,
              iseVolume19Id,
              iseVolume19RaidType,
              iseVolume19Pool,
              iseVolume19AllocationType,
              iseVolume19CacheType,
              iseVolume19Size,
              iseVolume19StatusStr,
              iseVolume19StatusDetailsStr,
              iseVolume19IsSnapshot,
              iseVolume19SnapshotChildId,
              iseVolume19SnapshotParentId,
--
              iseVolume20Name,
              iseVolume20VpdId,
              iseVolume20State,
              iseVolume20Status,
              iseVolume20Id,
              iseVolume20RaidType,
              iseVolume20Pool,
              iseVolume20AllocationType,
              iseVolume20CacheType,
              iseVolume20Size,
              iseVolume20StatusStr,
              iseVolume20StatusDetailsStr,
              iseVolume20IsSnapshot,
              iseVolume20SnapshotChildId,
              iseVolume20SnapshotParentId,
--
              iseVolume21Name,
              iseVolume21VpdId,
              iseVolume21State,
              iseVolume21Status,
              iseVolume21Id,
              iseVolume21RaidType,
              iseVolume21Pool,
              iseVolume21AllocationType,
              iseVolume21CacheType,
              iseVolume21Size,
              iseVolume21StatusStr,
              iseVolume21StatusDetailsStr,
              iseVolume21IsSnapshot,
              iseVolume21SnapshotChildId,
              iseVolume21SnapshotParentId,
--
              iseVolume22Name,
              iseVolume22VpdId,
              iseVolume22State,
              iseVolume22Status,
              iseVolume22Id,
              iseVolume22RaidType,
              iseVolume22Pool,
              iseVolume22AllocationType,
              iseVolume22CacheType,
              iseVolume22Size,
              iseVolume22StatusStr,
              iseVolume22StatusDetailsStr,
              iseVolume22IsSnapshot,
              iseVolume22SnapshotChildId,
              iseVolume22SnapshotParentId,
--
              iseVolume23Name,
              iseVolume23VpdId,
              iseVolume23State,
              iseVolume23Status,
              iseVolume23Id,
              iseVolume23RaidType,
              iseVolume23Pool,
              iseVolume23AllocationType,
              iseVolume23CacheType,
              iseVolume23Size,
              iseVolume23StatusStr,
              iseVolume23StatusDetailsStr,
              iseVolume23IsSnapshot,
              iseVolume23SnapshotChildId,
              iseVolume23SnapshotParentId,
--
              iseVolume24Name,
              iseVolume24VpdId,
              iseVolume24State,
              iseVolume24Status,
              iseVolume24Id,
              iseVolume24RaidType,
              iseVolume24Pool,
              iseVolume24AllocationType,
              iseVolume24CacheType,
              iseVolume24Size,
              iseVolume24StatusStr,
              iseVolume24StatusDetailsStr,
              iseVolume24IsSnapshot,
              iseVolume24SnapshotChildId,
              iseVolume24SnapshotParentId,
--
              iseVolume25Name,
              iseVolume25VpdId,
              iseVolume25State,
              iseVolume25Status,
              iseVolume25Id,
              iseVolume25RaidType,
              iseVolume25Pool,
              iseVolume25AllocationType,
              iseVolume25CacheType,
              iseVolume25Size,
              iseVolume25StatusStr,
              iseVolume25StatusDetailsStr,
              iseVolume25IsSnapshot,
              iseVolume25SnapshotChildId,
              iseVolume25SnapshotParentId,
--
              iseVolume26Name,
              iseVolume26VpdId,
              iseVolume26State,
              iseVolume26Status,
              iseVolume26Id,
              iseVolume26RaidType,
              iseVolume26Pool,
              iseVolume26AllocationType,
              iseVolume26CacheType,
              iseVolume26Size,
              iseVolume26StatusStr,
              iseVolume26StatusDetailsStr,
              iseVolume26IsSnapshot,
              iseVolume26SnapshotChildId,
              iseVolume26SnapshotParentId,
--
              iseVolume27Name,
              iseVolume27VpdId,
              iseVolume27State,
              iseVolume27Status,
              iseVolume27Id,
              iseVolume27RaidType,
              iseVolume27Pool,
              iseVolume27AllocationType,
              iseVolume27CacheType,
              iseVolume27Size,
              iseVolume27StatusStr,
              iseVolume27StatusDetailsStr,
              iseVolume27IsSnapshot,
              iseVolume27SnapshotChildId,
              iseVolume27SnapshotParentId,
--
              iseVolume28Name,
              iseVolume28VpdId,
              iseVolume28State,
              iseVolume28Status,
              iseVolume28Id,
              iseVolume28RaidType,
              iseVolume28Pool,
              iseVolume28AllocationType,
              iseVolume28CacheType,
              iseVolume28Size,
              iseVolume28StatusStr,
              iseVolume28StatusDetailsStr,
              iseVolume28IsSnapshot,
              iseVolume28SnapshotChildId,
              iseVolume28SnapshotParentId
--
 
-- ** VOLUME GROUP DEFINITIONS END  
		   }
    STATUS       current              
    DESCRIPTION "A collection of Volume attribute objects"
    ::= { iseMIBGroups 7 }                                      -- 1.3.6.1.4.1.2366.6.1.2.4.1.7
    
hostGroup OBJECT-GROUP
   OBJECTS { 
-- ** HOST GROUP DEFINITIONS BEGIN
  

             iseHost1Name,
             iseHost1Os,
             iseHost1Id,
             iseHost1StatusStr,
             iseHost1StatusDetailsStr,
--
             iseHost2Name,
             iseHost2Os,
             iseHost2Id,
             iseHost2StatusStr,
             iseHost2StatusDetailsStr,
--
             iseHost3Name,
             iseHost3Os,
             iseHost3Id,
             iseHost3StatusStr,
             iseHost3StatusDetailsStr,
--
             iseHost4Name,
             iseHost4Os,
             iseHost4Id,
             iseHost4StatusStr,
             iseHost4StatusDetailsStr,
--
             iseHost5Name,
             iseHost5Os,
             iseHost5Id,
             iseHost5StatusStr,
             iseHost5
--
 
-- ** HOST GROUP DEFINITIONS END
		   }
    STATUS       current              
    DESCRIPTION "A collection of Host attribute objects"
    ::= { iseMIBGroups 8 }                                      -- 1.3.6.1.4.1.2366.6.1.2.4.1.8 

fcPortGroup OBJECT-GROUP
    OBJECTS {
               fcPort1WWN,
               fcPort1Status,
               fcPort1StatusStr,
               fcPort1Type,
               fcPort1Speed,
--               
               fcPort2WWN,
               fcPort2Status,
               fcPort2StatusStr,
               fcPort2Type,
               fcPort2Speed,
--               
               fcPort3WWN,
               fcPort3Status,
               fcPort3StatusStr,
               fcPort3Type,
               fcPort3Speed,
--               
               fcPort4WWN,
               fcPort4Status,
               fcPort4StatusStr,
               fcPort4Type,
               fcPort4Speed,
--               
               fcPort5WWN,
               fcPort5Status,
               fcPort5StatusStr,
               fcPort5Type,
               fcPort5Speed,
--               
               fcPort6WWN,
               fcPort6Status,
               fcPort6StatusStr,
               fcPort6Type,
               fcPort6Speed,
--               
               fcPort7WWN,
               fcPort7Status,
               fcPort7StatusStr,
               fcPort7Type,
               fcPort7Speed,
--               
               fcPort8WWN,
               fcPort8Status,
               fcPort8StatusStr,
               fcPort8Type,
               fcPort8Speed           
		   }               
    
    STATUS       current              
    DESCRIPTION "A collection of FcPort attribute objects"
    ::= { iseMIBGroups 9 }                                      -- 1.3.6.1.4.1.2366.6.1.2.4.1.9   

sfpGroup OBJECT-GROUP
    OBJECTS {
               sfp1Id,
               sfp1IsPresent,
               sfp1Status,               
               sfp1StatusStr,
               sfp1HardwareVersion,
               sfp1SerialNum,
               sfp1PartNum,
--               
               sfp2Id,
               sfp2IsPresent,
               sfp2Status,               
               sfp2StatusStr,
               sfp2HardwareVersion,
               sfp2SerialNum,
               sfp2PartNum,
--               
               sfp3Id,
               sfp3IsPresent,
               sfp3Status,               
               sfp3StatusStr,
               sfp3HardwareVersion,
               sfp3SerialNum,
               sfp3PartNum,
--               
               sfp4Id,
               sfp4IsPresent,
               sfp4Status,               
               sfp4StatusStr,
               sfp4HardwareVersion,
               sfp4SerialNum,
               sfp4PartNum,
--               
               sfp5Id,
               sfp5IsPresent,
               sfp5Status,               
               sfp5StatusStr,
               sfp5HardwareVersion,
               sfp5SerialNum,
               sfp5PartNum,
--               
               sfp6Id,
               sfp6IsPresent,
               sfp6Status,               
               sfp6StatusStr,
               sfp6HardwareVersion,
               sfp6SerialNum,
               sfp6PartNum,
--               
               sfp7Id,
               sfp7IsPresent,
               sfp7Status,               
               sfp7StatusStr,
               sfp7HardwareVersion,
               sfp7SerialNum,
               sfp7PartNum,
--               
               sfp8Id,
               sfp8IsPresent,
               sfp8Status,               
               sfp8StatusStr,
               sfp8HardwareVersion,
               sfp8SerialNum,
               sfp8PartNum       
		   }               
    
    STATUS       current              
    DESCRIPTION "A collection of SFP attribute objects"
    ::= { iseMIBGroups 10 }                                      -- 1.3.6.1.4.1.2366.6.1.2.4.1.10  
    
--
-- Trap Definitions  ***********************************************************************
--

-- iseNotification = 1.3.6.1.4.1.2366.6.1.2.3

iseAgentTrapVals    OBJECT IDENTIFIER ::= { iseNotification 1 }   -- 1.3.6.1.4.1.2366.6.1.2.3.1
fwEventTrapVals  OBJECT IDENTIFIER ::= { iseNotification 2 }      -- 1.3.6.1.4.1.2366.6.1.2.3.2
celEventTrapVals OBJECT IDENTIFIER ::= { iseNotification 3 }      -- 1.3.6.1.4.1.2366.6.1.2.3.3
iseTraps         OBJECT IDENTIFIER ::= { iseNotification 4 }      -- 1.3.6.1.4.1.2366.6.1.2.3.4

 
--  ***********************  Agent Trap  *************************
agentEventTrap NOTIFICATION-TYPE
OBJECTS {iseName, isePhysicalLocation, agentEventDescription }  
STATUS	current
DESCRIPTION
	"Agent Event Trap."
::= { iseAgentTrapVals 1 }      --  1.3.6.1.4.1.2366.6.1.2.3.1.1

agentEventSystemNum OBJECT-TYPE
SYNTAX Integer32
MAX-ACCESS accessible-for-notify
STATUS	current
DESCRIPTION
	"Agent subsystem originating the trap."
::= { iseAgentTrapVals 2 }      --  1.3.6.1.4.1.2366.6.1.2.3.1.2

agentEventFunctionNum OBJECT-TYPE
SYNTAX Integer32
MAX-ACCESS accessible-for-notify
STATUS	current
DESCRIPTION
	"Agent subsystem function originating the trap"
::= { iseAgentTrapVals 3 }      --  1.3.6.1.4.1.2366.6.1.2.3.1.3

agentEventCode OBJECT-TYPE
SYNTAX Integer32
MAX-ACCESS accessible-for-notify
STATUS	current
DESCRIPTION
	"Event Code"
::= { iseAgentTrapVals 4 }      --  1.3.6.1.4.1.2366.6.1.2.3.1.4

agentEventDescription OBJECT-TYPE
SYNTAX DisplayString
MAX-ACCESS accessible-for-notify
STATUS	current
DESCRIPTION
	"Agent Event Description."
::= { iseAgentTrapVals 5 }      --  1.3.6.1.4.1.2366.6.1.2.3.1.5


-- ****************************  Firmware Event Trap ***************************

fwEventType OBJECT-TYPE
SYNTAX Integer32
MAX-ACCESS accessible-for-notify
STATUS	current
DESCRIPTION
	"Firmware Event type."
::= { fwEventTrapVals 2 }      --  1.3.6.1.4.1.2366.6.1.2.3.2.2

fwEventComponent OBJECT-TYPE
SYNTAX Integer32
MAX-ACCESS accessible-for-notify
STATUS	current
DESCRIPTION  
  "Firmware Event Component."                                                                                                             
::= { fwEventTrapVals 3 }      --  1.3.6.1.4.1.2366.6.1.2.3.2.3
	
fwEventClass OBJECT-TYPE
SYNTAX Integer32
MAX-ACCESS accessible-for-notify
STATUS	current
DESCRIPTION
	"Firmware Event Class."
::= { fwEventTrapVals 4 }      --  1.3.6.1.4.1.2366.6.1.2.3.2.4

fwEventDescription OBJECT-TYPE
SYNTAX DisplayString
MAX-ACCESS accessible-for-notify
STATUS	current
DESCRIPTION
	"Firmware Event Description."
::= { fwEventTrapVals 5 }      --  1.3.6.1.4.1.2366.6.1.2.3.2.5

fwEventTrap NOTIFICATION-TYPE
OBJECTS { iseName, isePhysicalLocation, iseAdminName,
          fwEventType, fwEventComponent, fwEventClass, fwEventDescription  }
STATUS	current
DESCRIPTION
	"Firmware Event."
::= { fwEventTrapVals 1 }      --  1.3.6.1.4.1.2366.6.1.2.3.2.1

-- *****************************
-- ****************************  CEL Event Trap ***************************
-- *****************************

celEventType OBJECT-TYPE
SYNTAX Integer32
MAX-ACCESS accessible-for-notify
STATUS	current
DESCRIPTION
	"Firmware Event type."
::= { celEventTrapVals 2 }      --  1.3.6.1.4.1.2366.6.1.2.3.3.2

celEventComponent OBJECT-TYPE
SYNTAX Integer32
MAX-ACCESS accessible-for-notify
STATUS	current
DESCRIPTION  
  "Firmware Event Component."                                                                                                             
::= { celEventTrapVals 3 }      --  1.3.6.1.4.1.2366.6.1.2.3.3.3
	
celEventClass OBJECT-TYPE
SYNTAX Integer32
MAX-ACCESS accessible-for-notify
STATUS	current
DESCRIPTION
	"Firmware Event Class."
::= { celEventTrapVals 4 }      --  1.3.6.1.4.1.2366.6.1.2.3.3.4

celEventDescription OBJECT-TYPE
SYNTAX DisplayString
MAX-ACCESS accessible-for-notify
STATUS	current
DESCRIPTION
	"Firmware Event Description."
::= { celEventTrapVals 5 }      --  1.3.6.1.4.1.2366.6.1.2.3.3.5

celEventVolumeIndex OBJECT-TYPE
SYNTAX Integer32
MAX-ACCESS accessible-for-notify
STATUS	current
DESCRIPTION
	"Volume Event - Volume Index."
::= { celEventTrapVals 6 }      --  1.3.6.1.4.1.2366.6.1.2.3.3.6
 	
celEventVolumeName OBJECT-TYPE
SYNTAX DisplayString
MAX-ACCESS accessible-for-notify
STATUS	current
DESCRIPTION
	"Volume Event - Volume Name."
::= { celEventTrapVals 7 }      --  1.3.6.1.4.1.2366.6.1.2.3.3.7

celEventVolumeRaidType OBJECT-TYPE
SYNTAX Integer32
                {
                  raid0(0),
                  raid1(1),
                  raid5(5),
                  raid6(6)
                 }
MAX-ACCESS accessible-for-notify
STATUS	current
DESCRIPTION
	"Volume Event - Volume Raid Type."
::= { celEventTrapVals 8 }      --  1.3.6.1.4.1.2366.6.1.2.3.3.8

celEventVolumePoolId OBJECT-TYPE
SYNTAX Integer32
MAX-ACCESS accessible-for-notify
STATUS	current
DESCRIPTION
	"Volume Event - Volume Pool ID."
::= { celEventTrapVals 9 }      --  1.3.6.1.4.1.2366.6.1.2.3.3.9

-- celEventVolumeAllocType is deprecated **********************************
celEventVolumeAllocType OBJECT-TYPE
SYNTAX Integer32
MAX-ACCESS accessible-for-notify
STATUS	current
DESCRIPTION
	"Volume Event - Volume Allocation Type."
::= { celEventTrapVals 10 }      --  1.3.6.1.4.1.2366.6.1.2.3.3.10

celEventVolumeCacheMode OBJECT-TYPE
SYNTAX Integer32
                {
                  writeBack(0),
                  writeThrough(1)
                }
MAX-ACCESS accessible-for-notify
STATUS	current
DESCRIPTION
	"Volume Event - Volume Cache Mode."
::= { celEventTrapVals 11 }      --  1.3.6.1.4.1.2366.6.1.2.3.3.11

celEventVolumeSize OBJECT-TYPE
SYNTAX Integer32
MAX-ACCESS accessible-for-notify
STATUS	current
DESCRIPTION
	"Volume Event - Volume Size."
::= { celEventTrapVals 12 }      --  1.3.6.1.4.1.2366.6.1.2.3.3.12

celEventSubSystem OBJECT-TYPE
SYNTAX Integer32
                {
                  powerSupply(1),
                  mrc(2),
                  displayCard(3),
                  dataPac(5),
                  battery(6),
                  sfpFcTransceiver(7)
                 }
MAX-ACCESS accessible-for-notify
STATUS	current
DESCRIPTION
	"CEL Event - Subsystem number."
::= { celEventTrapVals 13 }      --  1.3.6.1.4.1.2366.6.1.2.3.3.13

celEventSubSystemName OBJECT-TYPE
SYNTAX DisplayString
MAX-ACCESS accessible-for-notify
STATUS	current
DESCRIPTION
	"CEL Event - Subsystem Name."
::= { celEventTrapVals 14 }      --  1.3.6.1.4.1.2366.6.1.2.3.3.14

celEventSubSystemInstance OBJECT-TYPE
SYNTAX Integer32
MAX-ACCESS accessible-for-notify
STATUS	current
DESCRIPTION
	"CEL Event - Subsystem Instance."
::= { celEventTrapVals 15 }      --  1.3.6.1.4.1.2366.6.1.2.3.3.15

celEventSubSystemTemp OBJECT-TYPE
SYNTAX Integer32
MAX-ACCESS accessible-for-notify
STATUS	current
DESCRIPTION
	"CEL Event - Subsystem Temperature."
::= { celEventTrapVals 16 }      --  1.3.6.1.4.1.2366.6.1.2.3.3.16

celEventFruStatus OBJECT-TYPE
SYNTAX Integer32
MAX-ACCESS accessible-for-notify
STATUS	current
DESCRIPTION
	"CEL Event - Current FRU Status."
::= { celEventTrapVals 17 }      --  1.3.6.1.4.1.2366.6.1.2.3.3.17

celEventFruLastStatus OBJECT-TYPE
SYNTAX Integer32
MAX-ACCESS accessible-for-notify
STATUS	current
DESCRIPTION
	"CEL Event - Previous FRU Status."
::= { celEventTrapVals 18 }      --  1.3.6.1.4.1.2366.6.1.2.3.3.18

celEventInsertRemoveEventCode OBJECT-TYPE
SYNTAX Integer32
                {
                  inserted(1),
                  removed(2)
                }
MAX-ACCESS accessible-for-notify
STATUS	current
DESCRIPTION
	"CEL Event - FRU Insertion or Removal Event Code - value of 1 equals an Insertion."
::= { celEventTrapVals 19 }      --  1.3.6.1.4.1.2366.6.1.2.3.3.19

celEventMRCCacheMode OBJECT-TYPE
SYNTAX Integer32
                {
                  writeBack(0),
                  writeThrough(1)
                }
MAX-ACCESS accessible-for-notify
STATUS	current
DESCRIPTION
	"CEL Event - Cache Policy changed. 0 = Policy changed TO Write Back,  1 = Policy changed TO Write Through."
::= { celEventTrapVals 20 }      --  1.3.6.1.4.1.2366.6.1.2.3.3.20

agentEventHostName OBJECT-TYPE
SYNTAX DisplayString
MAX-ACCESS accessible-for-notify
STATUS	current
DESCRIPTION
	"Host Event - Host Name."
::= { celEventTrapVals 21 }      --  1.3.6.1.4.1.2366.6.1.2.3.3.21

agentEventHostIndex OBJECT-TYPE
SYNTAX Integer32
MAX-ACCESS accessible-for-notify
STATUS	current
DESCRIPTION
	"Host Event - Host Index."
::= { celEventTrapVals 22 }      --  1.3.6.1.4.1.2366.6.1.2.3.3.22

agentEventHostOsType OBJECT-TYPE
SYNTAX DisplayString
MAX-ACCESS accessible-for-notify
STATUS	current
DESCRIPTION
	"Host Event - Host OS Type."
::= { celEventTrapVals 23 }      --  1.3.6.1.4.1.2366.6.1.2.3.3.23

celEventDataPacRemoveStatus OBJECT-TYPE
SYNTAX Integer32
                {
                  toBeRemoved(2),
                  removed(7),
                  singleDataPac(11),
                  hasVolumes(12),
                  noResource(13),
                  dssEraseInProgress(14),
                  dssEraseFailed(15),
                  dssReaseAborted(16),
                  taskInvalidPhase(19),
                  configEventInProgress(28)                  
                }
MAX-ACCESS accessible-for-notify
STATUS	current
DESCRIPTION
	"CEL Event - DataPac Remove - status code"
::= { celEventTrapVals 24 }      --  1.3.6.1.4.1.2366.6.1.2.3.3.24

celEventDataPacAddStatus OBJECT-TYPE
SYNTAX Integer32
                {
                  toBeAdded(1),
                  handleFailure(3),
                  onlineFailure(4),
                  added(6),
                  alreadyInitialized(10),
                  noResource(13),
                  taskInvalidPhase(19),
                  addFailed(26),
                  configEventInProgress(28)                  
                }
MAX-ACCESS accessible-for-notify
STATUS	current
DESCRIPTION
	"CEL Event - DataPac Add - status code"
::= { celEventTrapVals 25 }      --  1.3.6.1.4.1.2366.6.1.2.3.3.25

celEventMrcId OBJECT-TYPE
SYNTAX Integer32
MAX-ACCESS accessible-for-notify
STATUS	current
DESCRIPTION
	"CEL Event - MRC ID"
::= { celEventTrapVals 26 }      --  1.3.6.1.4.1.2366.6.1.2.3.3.26

celEventIseXO OBJECT-TYPE
SYNTAX Integer32
MAX-ACCESS accessible-for-notify
STATUS	current
DESCRIPTION
	"CEL Event - ISE XO MRC"
::= { celEventTrapVals 27 }      --  1.3.6.1.4.1.2366.6.1.2.3.3.27

celSystemInoperativeReasonCode OBJECT-TYPE
SYNTAX Integer32
                {
                  smldInoperative(1),
                  bufferscanInoperative(2),
                  testbufferInoperative(3),
                  dataCacheUnavailable(4),
                  metadataIncompatible(5)                
                }
MAX-ACCESS accessible-for-notify
STATUS	current
DESCRIPTION
	"CEL Event - System Inoperative Reason Code"
::= { celEventTrapVals 28 }      --  1.3.6.1.4.1.2366.6.1.2.3.3.28

celLDInoperativeReasonCode OBJECT-TYPE
SYNTAX Integer32
               {
                 cacheDataLost(1),
                 otherReason(2)
               }
MAX-ACCESS accessible-for-notify
STATUS	current
DESCRIPTION
	"CEL Event - Logical Disk (Volume) Inoperative Reason Code"
::= { celEventTrapVals 29 }      --  1.3.6.1.4.1.2366.6.1.2.3.3.29

celLDDIndex OBJECT-TYPE
SYNTAX Integer32
MAX-ACCESS accessible-for-notify
STATUS	current
DESCRIPTION
	"CEL Event - Unit Cache Event - LDD Index"
::= { celEventTrapVals 30 }      --  1.3.6.1.4.1.2366.6.1.2.3.3.30

celDriveSpotLocation OBJECT-TYPE
SYNTAX Integer32
MAX-ACCESS accessible-for-notify
STATUS	current
DESCRIPTION
	"CEL Event - Drive Spot Location"
::= { celEventTrapVals 31 }      --  1.3.6.1.4.1.2366.6.1.2.3.3.31

celDataPacID OBJECT-TYPE
SYNTAX Integer32
MAX-ACCESS accessible-for-notify
STATUS	current
DESCRIPTION
	"CEL Event - DataPac ID"
::= { celEventTrapVals 32 }      --  1.3.6.1.4.1.2366.6.1.2.3.3.32

celDriveState OBJECT-TYPE
SYNTAX Integer32
                {
                  unknown(0),
                  notInstalled(10),
                  missing(11),
                  failed(12),
                  disruptive(13),
                  slow(14),
                  offline(20),
                  inFwLoad(21),
                  inReman(22),
                  inReformat(23),
                  inDiag(24),
                  good(40),
                  needsFwLoad(41),
                  needsReman(42),
                  needsReformat(43),
                  needsDiag(44),
                  needsPwrCycle(45),
                  needsReset(46),
                  needsDisable(47)
                }
                  
                  
MAX-ACCESS accessible-for-notify
STATUS	current
DESCRIPTION
	"CEL Event - Drive State"
::= { celEventTrapVals 33 }      --  1.3.6.1.4.1.2366.6.1.2.3.3.33

agentEventHttpIpAddress OBJECT-TYPE
SYNTAX DisplayString
MAX-ACCESS accessible-for-notify
STATUS	current
DESCRIPTION
	"Login Event - IP Address of HTTP Client."
::= { celEventTrapVals 34 }      --  1.3.6.1.4.1.2366.6.1.2.3.3.34

agentEventUserName OBJECT-TYPE
SYNTAX DisplayString
MAX-ACCESS accessible-for-notify
STATUS	current
DESCRIPTION
	"Login Event - User Name."
::= { celEventTrapVals 35 }      --  1.3.6.1.4.1.2366.6.1.2.3.3.35

fwUpgradeFailedCode OBJECT-TYPE
SYNTAX Integer32
MAX-ACCESS accessible-for-notify
STATUS	current
DESCRIPTION
	"FW UPgrade Event - Firmware Upgrade Failed Error Code"
::= { celEventTrapVals 36 }      --  1.3.6.1.4.1.2366.6.1.2.3.3.36

celDataPacStatus OBJECT-TYPE
SYNTAX Integer32
                {
                  healthy(0),
                  degraded(1),
                  inoperative(2)
                }
MAX-ACCESS accessible-for-notify
STATUS	current
DESCRIPTION
	"DataPac Status Code"
::= { celEventTrapVals 37 }      --  1.3.6.1.4.1.2366.6.1.2.3.3.37

celDataPacMeltReasonCode OBJECT-TYPE
SYNTAX Integer32
                {
                  tooManyDriveFailures(1)
                }
MAX-ACCESS accessible-for-notify
STATUS	current
DESCRIPTION
	"DataPac Inoperative Reason Code"
::= { celEventTrapVals 38 }      --  1.3.6.1.4.1.2366.6.1.2.3.3.38


celMrcErrorCode OBJECT-TYPE
SYNTAX Integer32
                {
                  badRTC(1),
                  pendingEscEvent(2),
                  upsupportedVPD(4),
                  deadBeat(8),
                  badTemperature(32),
                  otherMrcReset(64),
                  cacheBackupFailed(128),
                  mrcNotPresent(256),
                  badVpdCRC(1024),
                  badVpdType(2048),
                  badVpdVersion(4096),
                  badVpd(8192),
                  persistentFault(32768) 
                }
MAX-ACCESS accessible-for-notify
STATUS	current
DESCRIPTION
	"MRC Error Code"
::= { celEventTrapVals 39 }      --  1.3.6.1.4.1.2366.6.1.2.3.3.39

celDataPacErrorCode OBJECT-TYPE
SYNTAX Integer32
MAX-ACCESS accessible-for-notify
STATUS	current
DESCRIPTION
	"DataPac Error Code - use CelViewer to translate this Mask value"
::= { celEventTrapVals 40 }      --  1.3.6.1.4.1.2366.6.1.2.3.3.40

celPowerSupplyErrorCode OBJECT-TYPE
SYNTAX Integer32
                {
                  badAC(2),
                  badDC(4),
                  badFan(32),
                  badPower(64),
                  highTemperature(128),
                  psNotPresent(256),
                  psOffline(512),
                  badVpdCRC(1024),
                  badVpdType(2048),
                  badVpdVersion(4096),
                  badVpd(8192),
                  persistentFault(32768) 
                }
MAX-ACCESS accessible-for-notify
STATUS	current
DESCRIPTION
	"Power Supply Error Code"
::= { celEventTrapVals 41 }      --  1.3.6.1.4.1.2366.6.1.2.3.3.41


celEventFruId OBJECT-TYPE
SYNTAX Integer32
MAX-ACCESS accessible-for-notify
STATUS	current
DESCRIPTION
	"FRU ID = FRU Instance = 0 or 1 "
::= { celEventTrapVals 43 }      --  1.3.6.1.4.1.2366.6.1.2.3.3.43


redundancyLostReasonCode OBJECT-TYPE
SYNTAX Integer32
                {
                  firmwareCrashFailure(1),
                  mrcAddReset(2),
                  watcherCrash(4),
                  lfuCrash(8),
                  unknownKernalRestart(16),
                  iseShutdownRestart(32),
                  faultInsert(64),
                  powerFailed(128),
                  watchdogReset(256),
                  watchdogISR(512),
                  kernelPanic(1024),
                  iseShutdown(2048),
                  iseReboot(4096),
                  sympathyCrash(8192),
                  firmwareInstigator(16384)                     
                }
MAX-ACCESS accessible-for-notify
STATUS	current
DESCRIPTION
	"Redundancy Lost Reason Code"
::= { celEventTrapVals 46 }      --  1.3.6.1.4.1.2366.6.1.2.3.3.46

celFanStatus  OBJECT-TYPE
SYNTAX Integer32
                {
                  fan1Ps1Failed(1),
                  fan2Ps1Failed(2),
                  fan1Ps2Failed(4),
                  fan1Ps2Failed(8)                   
                }
MAX-ACCESS accessible-for-notify
STATUS	current
DESCRIPTION
	"Fan Status Code"
::= { celEventTrapVals 47 }      --  1.3.6.1.4.1.2366.6.1.2.3.3.47

celFanId OBJECT-TYPE
SYNTAX Integer32
MAX-ACCESS accessible-for-notify
STATUS	current
DESCRIPTION
	"Fan ID = 0 or 1 "
::= { celEventTrapVals 48 }      --  1.3.6.1.4.1.2366.6.1.2.3.3.48

celEventVolumeSnapshotType  OBJECT-TYPE
SYNTAX Integer32
                {
                  primaryVolume(0),
                  fullyAllocated(1),
                  spaceEfficient(2),
                  snapClone(3)                   
                }
MAX-ACCESS accessible-for-notify
STATUS	current
DESCRIPTION
	"Type of Snapshot being created"
::= { celEventTrapVals 49 }      --  1.3.6.1.4.1.2366.6.1.2.3.3.49

celCcsOperationStatus OBJECT-TYPE
SYNTAX Integer32
                {
                  success(0),
                  failure(1),
                  oPprogress(2),
                  noResource(4),
                  lunBusy(5),
                  invalidID(6),
                  invalidCommand(11),
                  invalidArgument(12),
                  unknownTask(13),
                  unknownLdId(14),
                  unknownHBA(15),
                  unknownLUN(16),
                  fruStatusBad(17),
                  configEventOn(18),
                  iseReboot(19),
                  fruNotPresent(20),
                  prohibitedOperation(21),
                  shutdownAborted(22),
                  cachePolicyIneffect(23),
                  cacheModeSameAsRequested(24),
                  invalidState(25),
                  unsupported(26),
                  invalidSourceId(27),
                  invalidPoolState(28),
                  paramMismatch(29),
                  invalidSnapDelete(30),
                  volumePresented(31),
                  failbackActive(32),
                  invalidSourceState(33),
                  sourceNotWT(34),
                  noSpace(35),
                  maxObject(36),
                  volumeExist(37),
                  volumeNotFound(38),
                  invalidSize(39),
                  invalidCacheMode(40),
                  invalidRaidLevel(41),
                  invalidName(42),
                  subtypeMismatch(43),
                  singleDatapac(44),
                  fruOffline(45),
                  taskInvalidPhase(46),
                  fruFailure(47),
                  datapacCodeUpdate(48),
                  invalidPath(49),
                  fileNotFound(50),
                  fileOpenError(51),
                  fileStatError(52),
                  fileReadError(53),
                  invalidFwRev(54),
                  imageRejected(55),
                  codeUpdateFailed(56),
                  systemShutdown(57),
                  malformedScript(58),
                  taskAlreadyCompleted(59),
                  taskInUse(60),
                  taskInvalidOp(61),
                  noTargetConnection(62),
                  mastershipRequired(63),
                  unknownRemoteLD(64),
                  dataMigrationBusy(65),
                  remanInProgress(66),
                  reformatInProgress(67),
                  notAllowedOnNXO(68),
                  invalidShutdown(69),
                  cpmPending(70),
                  notInitialized(71),
                  waitInitialize(72),
                  restrictedMode(73),
                  restarting(74),
                  bootInProgress(75),
                  invalidMirrorState(76),
                  vmirrorMemberBusy(77),
                  objNameInUse(78),
                  s2sFailure(79),
                  generalS2SError(100)                                 
                }
MAX-ACCESS accessible-for-notify
STATUS	current
DESCRIPTION
	"CCS Operation Status Code"
::= { celEventTrapVals 50 }      --  1.3.6.1.4.1.2366.6.1.2.3.3.50

failedUpgradeString OBJECT-TYPE
SYNTAX DisplayString
MAX-ACCESS accessible-for-notify
STATUS	current
DESCRIPTION
	"Upgrade failure informative string"
::= { celEventTrapVals 51}      --  1.3.6.1.4.1.2366.6.1.2.3.3.51

restoredMrcIpAddress OBJECT-TYPE
SYNTAX DisplayString
MAX-ACCESS accessible-for-notify
STATUS	current
DESCRIPTION
	"IP Address of the restored MRC."
::= { celEventTrapVals 52}      --  1.3.6.1.4.1.2366.6.1.2.3.3.52

reportingMrcIpAddress OBJECT-TYPE
SYNTAX DisplayString
MAX-ACCESS accessible-for-notify
STATUS	current
DESCRIPTION
	"IP Address of the reporting MRC."
::= { celEventTrapVals 53 }      --  1.3.6.1.4.1.2366.6.1.2.3.3.53

spotLocation OBJECT-TYPE
SYNTAX Integer32
MAX-ACCESS accessible-for-notify
STATUS	current
DESCRIPTION
	"SPOT Location"
::= { celEventTrapVals 54 }      --  1.3.6.1.4.1.2366.6.1.2.3.3.54

dataPacHealth OBJECT-TYPE
SYNTAX Integer32
MAX-ACCESS accessible-for-notify
STATUS	current
DESCRIPTION
	"DataPac Health in Percentage"
::= { celEventTrapVals 55 }      --  1.3.6.1.4.1.2366.6.1.2.3.3.55


sfpId OBJECT-TYPE
SYNTAX Integer32
MAX-ACCESS accessible-for-notify
STATUS	current
DESCRIPTION
	"SFP ID (small form-factor pluggable)"
::= { celEventTrapVals 56 }      --  1.3.6.1.4.1.2366.6.1.2.3.3.56

sfpErrorCode OBJECT-TYPE
SYNTAX Integer32
MAX-ACCESS accessible-for-notify
STATUS	current
DESCRIPTION
	"SFP Error Code (small form-factor pluggable)"
::= { celEventTrapVals 57 }      --  1.3.6.1.4.1.2366.6.1.2.3.3.57

fruSerialNum OBJECT-TYPE
SYNTAX DisplayString
MAX-ACCESS accessible-for-notify
STATUS	current
DESCRIPTION
	"Serial Number of the FRU."
::= { celEventTrapVals 58 }      --  1.3.6.1.4.1.2366.6.1.2.3.3.58

mrcFwRev OBJECT-TYPE
SYNTAX Integer32
MAX-ACCESS accessible-for-notify
STATUS	current
DESCRIPTION
	"MRC Current Firmware Rev"
::= { celEventTrapVals 59 }      --  1.3.6.1.4.1.2366.6.1.2.3.3.59

displayCrdFwRev OBJECT-TYPE
SYNTAX Integer32
MAX-ACCESS accessible-for-notify
STATUS	current
DESCRIPTION
	"Display Card Current Firmware Rev"
::= { celEventTrapVals 60 }      --  1.3.6.1.4.1.2366.6.1.2.3.3.60

mrcCorrectFwRev OBJECT-TYPE
SYNTAX Integer32
MAX-ACCESS accessible-for-notify
STATUS	current
DESCRIPTION
	"Firmware Rev the MRC should be at"
::= { celEventTrapVals 61 }      --  1.3.6.1.4.1.2366.6.1.2.3.3.61

mrcMaintModeFlags OBJECT-TYPE
SYNTAX Integer32
MAX-ACCESS accessible-for-notify
STATUS	current
DESCRIPTION
	"MRC Maintenance Mode Flags"
::= { celEventTrapVals 62 }      --  1.3.6.1.4.1.2366.6.1.2.3.3.62

mrcMaintModeFlagsString OBJECT-TYPE
SYNTAX DisplayString
MAX-ACCESS accessible-for-notify
STATUS	current
DESCRIPTION
	"MRC Maintenance Mode Flags - translated to string"
::= { celEventTrapVals 63 }      --  1.3.6.1.4.1.2366.6.1.2.3.3.63

mrcInoperativeModeCode OBJECT-TYPE
SYNTAX Integer32
MAX-ACCESS accessible-for-notify
STATUS	current
DESCRIPTION
	"MRC Inoperative Mode Code"
::= { celEventTrapVals 64 }      --  1.3.6.1.4.1.2366.6.1.2.3.3.64

mrcInoperativeModeCodeString OBJECT-TYPE
SYNTAX DisplayString
MAX-ACCESS accessible-for-notify
STATUS	current
DESCRIPTION
	"MRC Inoperative Mode Code - translated to string"
::= { celEventTrapVals 65 }      --  1.3.6.1.4.1.2366.6.1.2.3.3.65

mrcDiagUtilModeCode OBJECT-TYPE
SYNTAX Integer32
MAX-ACCESS accessible-for-notify
STATUS	current
DESCRIPTION
	"MRC Diagnostic Utility Mode Code"
::= { celEventTrapVals 66 }      --  1.3.6.1.4.1.2366.6.1.2.3.3.66

mrcDiagUtilModeCodeString OBJECT-TYPE
SYNTAX DisplayString
MAX-ACCESS accessible-for-notify
STATUS	current
DESCRIPTION
	"MRC Diagnostic Utility Mode Code - translated to string"
::= { celEventTrapVals 67 }      --  1.3.6.1.4.1.2366.6.1.2.3.3.67

mrcGenerationNum OBJECT-TYPE
SYNTAX Integer32
MAX-ACCESS accessible-for-notify
STATUS	current
DESCRIPTION
	"MRC current Generation number"
::= { celEventTrapVals 68 }      --  1.3.6.1.4.1.2366.6.1.2.3.3.68

dataPacGenerationNum OBJECT-TYPE
SYNTAX Integer32
MAX-ACCESS accessible-for-notify
STATUS	current
DESCRIPTION
	"DataPac current Generation number"
::= { celEventTrapVals 69 }      --  1.3.6.1.4.1.2366.6.1.2.3.3.69

currentVersion OBJECT-TYPE
SYNTAX Integer32
MAX-ACCESS accessible-for-notify
STATUS	current
DESCRIPTION
	"Current Version"
::= { celEventTrapVals 74 }      --  1.3.6.1.4.1.2366.6.1.2.3.3.74

supportedVersion OBJECT-TYPE
SYNTAX Integer32
MAX-ACCESS accessible-for-notify
STATUS	current
DESCRIPTION
	"Supported Version"
::= { celEventTrapVals 75 }      --  1.3.6.1.4.1.2366.6.1.2.3.3.75

sfpSignalState OBJECT-TYPE
SYNTAX Integer32
                {
                  presentOrFaultCleared(0),
                  lostOrFaulted(1)                   
                }
MAX-ACCESS accessible-for-notify
STATUS	current
DESCRIPTION
	"SFP Signal State"
::= { celEventTrapVals 76 }      --  1.3.6.1.4.1.2366.6.1.2.3.3.76

sfpErrorCount  OBJECT-TYPE
SYNTAX Integer32
MAX-ACCESS accessible-for-notify
STATUS	current
DESCRIPTION
	"SFP Current Error Count"
::= { celEventTrapVals 77 }      --  1.3.6.1.4.1.2366.6.1.2.3.3.77

celDispCardErrorCode OBJECT-TYPE
SYNTAX Integer32
                {
                  degraded(2),
                  dispCardNotPresent(256),
                  dispCardOffline(512),
                  badVpdCRC(1024),
                  badVpdType(2048),
                  badVpdVersion(4096),
                  badVpd(8192),
                  persistentFault(32768) 
                }
MAX-ACCESS accessible-for-notify
STATUS	current
DESCRIPTION
	"Display Card Error Code"
::= { celEventTrapVals 78 }      --  1.3.6.1.4.1.2366.6.1.2.3.3.78

volumeGuidString OBJECT-TYPE
SYNTAX DisplayString
MAX-ACCESS accessible-for-notify
STATUS	current
DESCRIPTION
	"GUID of a Volume - in 1234-5678-9ABC-DEF1 form"
::= { celEventTrapVals 79 }      --  1.3.6.1.4.1.2366.6.1.2.3.3.79


vpdReasonCode OBJECT-TYPE
SYNTAX Integer32
                {
                  notDefined(0),
                  upsupportedVersion(1),
                  crcError(2)                   
                }
MAX-ACCESS accessible-for-notify
STATUS	current
DESCRIPTION
	"VPD Reason Code"
::= { celEventTrapVals 80 }      --  1.3.6.1.4.1.2366.6.1.2.3.3.80


vmirrorGuidString OBJECT-TYPE
SYNTAX DisplayString
MAX-ACCESS accessible-for-notify
STATUS	current
DESCRIPTION
	"GUID of a VMirror - in 1234-5678-9ABC-DEF1 form"
::= { celEventTrapVals 81 }      --  1.3.6.1.4.1.2366.6.1.2.3.3.81


vmirrorSize OBJECT-TYPE
SYNTAX Integer32
MAX-ACCESS accessible-for-notify
STATUS	current
DESCRIPTION
	"VMirrorEvent - VMirror Size."
::= { celEventTrapVals 82 }      --  1.3.6.1.4.1.2366.6.1.2.3.3.82


vmirrorOpStatusCode OBJECT-TYPE
SYNTAX Integer32
                {
                  success(0),
                  notRecovered(1),
                  difTag(2),   
                  defCrc(3),     
                  swFail(4),     
                  reConfig(5),     
                  misCompare(6)                     
                }
MAX-ACCESS accessible-for-notify
STATUS	current
DESCRIPTION
	"VMirror Status Code"
::= { celEventTrapVals 83 }      --  1.3.6.1.4.1.2366.6.1.2.3.3.83

vmirrorEventCode OBJECT-TYPE
SYNTAX Integer32
                {
                  synchComplete(0),
                  synchFailed(1),
                  mastershipMoved(2),   
                  vDiskLostMastership(3),     
                  vDiskLeftVMirror(4)                    
                }
MAX-ACCESS accessible-for-notify
STATUS	current
DESCRIPTION
	"VMirror State Change Event Code"
::= { celEventTrapVals 84 }      --  1.3.6.1.4.1.2366.6.1.2.3.3.84

superCapId OBJECT-TYPE
SYNTAX Integer32
MAX-ACCESS accessible-for-notify
STATUS	current
DESCRIPTION
	"SuperCapEvent - SuperCap ID."
::= { celEventTrapVals 85 }      --  1.3.6.1.4.1.2366.6.1.2.3.3.85

superCapVoltage OBJECT-TYPE
SYNTAX Integer32
MAX-ACCESS accessible-for-notify
STATUS	current
DESCRIPTION
	"SuperCapEvent - SuperCap Voltage."
::= { celEventTrapVals 86 }      --  1.3.6.1.4.1.2366.6.1.2.3.3.86

superCapErrorBitmask OBJECT-TYPE
SYNTAX Integer32
MAX-ACCESS accessible-for-notify
STATUS	current
DESCRIPTION
	 "SuperCap Error Bitmask.  Translate the error bitmask to determine the error
	    badRtc = 0x1
        inserted = 0x2
        removed = 0x4
        deadBeat = 0x8
        ableFault = 0x10
        badTemp = 0x20
        otherMrcReset = 0x40
        badVpdCookie = 0x80
        mrcNotPresent = 0x100
        badMrcOffline = 0x200
        badVpdCrc = 0x400
        badVpdType = 0x800
        badVpdVersion = 0x1000
        badVpd = 0x2000
        persistentFault = 0x8000"
::= { celEventTrapVals 87 }      --  1.3.6.1.4.1.2366.6.1.2.3.3.87

-- #define CEL_MIRROR_INDEX_OID "3.3.88.0"
mirrorIndex OBJECT-TYPE
SYNTAX Integer32
MAX-ACCESS accessible-for-notify
STATUS	current
DESCRIPTION
	"ISE Mirror Index."
::= { celEventTrapVals 88 }      --  1.3.6.1.4.1.2366.6.1.2.3.3.88

-- #define CEL_MIRROR_MEMBER_ID_OID "3.3.89.0"
mirrorMemberIndex OBJECT-TYPE
SYNTAX Integer32
MAX-ACCESS accessible-for-notify
STATUS	current
DESCRIPTION
	"ISE Mirror Member Index."
::= { celEventTrapVals 89 }      --  1.3.6.1.4.1.2366.6.1.2.3.3.89

-- #define CEL_DRIVES_IN_REPAIR_OID "3.3.90.0"
drivesInRepair OBJECT-TYPE
SYNTAX Integer32
MAX-ACCESS accessible-for-notify
STATUS	current
DESCRIPTION
	"Number of drives undergoing the repair process."
::= { celEventTrapVals 90 }      --  1.3.6.1.4.1.2366.6.1.2.3.3.90

-- #define CEL_MIRROR_CHANGE_MASK_OID "3.3.91.0"
mirrorChangeMask OBJECT-TYPE
SYNTAX Integer32
MAX-ACCESS accessible-for-notify
STATUS	current
DESCRIPTION
	"Mirror Attribute change Bitmask."
::= { celEventTrapVals 91 }      --  1.3.6.1.4.1.2366.6.1.2.3.3.91

-- #define CEL_MIRROR_CHANGE_MASK_OID "3.3.92.0"
memberWrites OBJECT-TYPE
SYNTAX Integer32
MAX-ACCESS accessible-for-notify
STATUS	current
DESCRIPTION
	"Mirror member writes"
::= { celEventTrapVals 92 }      --  1.3.6.1.4.1.2366.6.1.2.3.3.92

-- #define CEL_MIRROR_PING_CURRENT_LATENCY_OID "3.3.93.0"
currentLatency OBJECT-TYPE
SYNTAX Integer32
MAX-ACCESS accessible-for-notify
STATUS	current
DESCRIPTION
	"Current Mirror Ping Latency"
::= { celEventTrapVals 93 }      --  1.3.6.1.4.1.2366.6.1.2.3.3.93

-- #define CEL_MIRROR_PING_AVERAGE_LATENCY_OID "3.3.94.0"
currentLatency OBJECT-TYPE
SYNTAX Integer32
MAX-ACCESS accessible-for-notify
STATUS	current
DESCRIPTION
	"Average Mirror Ping Latency"
::= { celEventTrapVals 94 }      --  1.3.6.1.4.1.2366.6.1.2.3.3.94

-- *****************************************************************************
-- *****************************************************************************
-- *****************************************************************************

celEventTrap NOTIFICATION-TYPE
OBJECTS { iseName, isePhysicalLocation, iseAdminName,
          celEventType, celEventComponent, celEventClass, celEventDescription  }
STATUS	current
DESCRIPTION
	"Common Event Log Event."
::= { celEventTrapVals 1 }      --  1.3.6.1.4.1.2366.6.1.2.3.3.1


-- *****************************
-- *****************************  ISE Traps  ******************************
-- *****************************


storagePoolDeleted NOTIFICATION-TYPE
OBJECTS {iseName, isePhysicalLocation, fwEventDescription }  
STATUS	current
DESCRIPTION
	"Storage Pool Deleted."
::= { iseTraps 23 }      --  1.3.6.1.4.1.2366.6.1.2.3.4.23

iseInited NOTIFICATION-TYPE
OBJECTS {iseName, isePhysicalLocation, celEventDescription }  
STATUS	current
DESCRIPTION
	"ISE has been Initialized."
::= { iseTraps 79 }      --  1.3.6.1.4.1.2366.6.1.2.3.4.79

storagePoolInited NOTIFICATION-TYPE
OBJECTS {iseName, isePhysicalLocation, celEventDescription }  
STATUS	current
DESCRIPTION
	"Storage Pool Initialized"
::= { iseTraps 80 }      --  1.3.6.1.4.1.2366.6.1.2.3.4.80

volumeCreated NOTIFICATION-TYPE
OBJECTS {iseName, isePhysicalLocation, celEventDescription, celEventVolumeIndex, celEventVolumeName, celEventVolumeRaidType, celEventVolumePoolId, celEventVolumeCacheMode, celEventVolumeSize }  
STATUS	current
DESCRIPTION
	"Volume Created Event."
::= { iseTraps 81 }      --  1.3.6.1.4.1.2366.6.1.2.3.4.81

volumeDeleted NOTIFICATION-TYPE
OBJECTS {iseName, isePhysicalLocation, celEventDescription, celEventVolumeIndex }  
STATUS	current
DESCRIPTION
	"Volume Delete."
::= { iseTraps 82 }      --  1.3.6.1.4.1.2366.6.1.2.3.4.82
 
volumeInoperative  NOTIFICATION-TYPE
OBJECTS {iseName, isePhysicalLocation, celEventDescription, celEventVolumeIndex, celLDInoperativeReasonCode }  
STATUS	current
DESCRIPTION
	"A Volume is in Inoperative."
::= { iseTraps 83 }      --  1.3.6.1.4.1.2366.6.1.2.3.4.83
 
systemShuttingDown  NOTIFICATION-TYPE
OBJECTS {iseName, isePhysicalLocation, celEventDescription }  
STATUS	current
DESCRIPTION
	"ISE is Shutting Down."
::= { iseTraps 85 }      --  1.3.6.1.4.1.2366.6.1.2.3.4.85

mrcInserted NOTIFICATION-TYPE
OBJECTS {iseName, isePhysicalLocation, celEventDescription, celEventMrcId }  
STATUS	current
DESCRIPTION
	"MRC Inserted."
::= { iseTraps 87 }      --  1.3.6.1.4.1.2366.6.1.2.3.4.87

dataPacRemoved NOTIFICATION-TYPE
OBJECTS {iseName, isePhysicalLocation, celEventDescription, celEventSubSystemInstance, celEventDataPacRemoveStatus }  
STATUS	current
DESCRIPTION
	"DataPac Removed."
::= { iseTraps 88 }      --  1.3.6.1.4.1.2366.6.1.2.3.4.88

dataPacAdded NOTIFICATION-TYPE
OBJECTS {iseName, isePhysicalLocation, celEventDescription, celEventSubSystemInstance, celEventDataPacAddStatus }  
STATUS	current
DESCRIPTION
	"DataPac Added."
::= { iseTraps 89 }      --  1.3.6.1.4.1.2366.6.1.2.3.4.89

driveCodeUpdated NOTIFICATION-TYPE
OBJECTS {iseName, isePhysicalLocation, celEventDescription }  
STATUS	current
DESCRIPTION
	"Drive code is Updated."
::= { iseTraps 90 }      --  1.3.6.1.4.1.2366.6.1.2.3.4.90

fruCriticalTemp NOTIFICATION-TYPE
OBJECTS {iseName, isePhysicalLocation, celEventDescription, celEventSubSystem, celEventSubSystemName, celEventSubSystemInstance, celEventSubSystemTemp }  
STATUS	current
DESCRIPTION
	"FRU has reached Critical Temperature."
::= { iseTraps 114 }      --  1.3.6.1.4.1.2366.6.1.2.3.4.114

fruWarningTemp NOTIFICATION-TYPE
OBJECTS {iseName, isePhysicalLocation, celEventDescription, celEventSubSystem, celEventSubSystemName, celEventSubSystemInstance, celEventSubSystemTemp }  
STATUS	current
DESCRIPTION
	"FRU has reached Warning Temperature."
::= { iseTraps 115 }      --  1.3.6.1.4.1.2366.6.1.2.3.4.115

fruRemovalInsertion NOTIFICATION-TYPE
OBJECTS {iseName, isePhysicalLocation, celEventDescription, celEventSubSystem, celEventSubSystemName, celEventSubSystemInstance, celEventInsertRemoveEventCode }  
STATUS	current
DESCRIPTION
	"A FRU has been Inserted or Removed."
::= { iseTraps 116 }      --  1.3.6.1.4.1.2366.6.1.2.3.4.116

fruNormalTemp NOTIFICATION-TYPE
OBJECTS {iseName, isePhysicalLocation, celEventDescription, celEventSubSystem, celEventSubSystemName, celEventSubSystemInstance, celEventSubSystemTemp } 
STATUS	current
DESCRIPTION
	"FRU has returned to Normal Temperature."
::= { iseTraps 118 }      --  1.3.6.1.4.1.2366.6.1.2.3.4.118

mrcRemovedHotBoot NOTIFICATION-TYPE
OBJECTS {iseName, isePhysicalLocation, celEventDescription, celEventMrcId }  
STATUS	current
DESCRIPTION
	"MRC Removed."
::= { iseTraps 138 }      --  1.3.6.1.4.1.2366.6.1.2.3.4.138

mrcRemovedColdBoot NOTIFICATION-TYPE
OBJECTS {iseName, isePhysicalLocation, celEventDescription, celEventMrcId }  
STATUS	current
DESCRIPTION
	"MRC Removed - Cold Boot."
::= { iseTraps 139 }      --  1.3.6.1.4.1.2366.6.1.2.3.4.139

systemInoperativeColdBoot  NOTIFICATION-TYPE
OBJECTS {iseName, isePhysicalLocation, celEventDescription, celEventMrcId, celEventIseXO, celSystemInoperativeReasonCode }  
STATUS	current
DESCRIPTION
	"ISE Inoperative - Cold Boot"
::= { iseTraps 140 }      --  1.3.6.1.4.1.2366.6.1.2.3.4.140

mrcOfflineColdBoot NOTIFICATION-TYPE
OBJECTS {iseName, isePhysicalLocation, celEventDescription, celEventMrcId }  
STATUS	current
DESCRIPTION
	"MRC Offline - Cold Boot."
::= { iseTraps 141 }      --  1.3.6.1.4.1.2366.6.1.2.3.4.141
 
cacheModeChange NOTIFICATION-TYPE
OBJECTS {iseName, isePhysicalLocation, celEventDescription, celEventMRCCacheMode }  
STATUS	current
DESCRIPTION
	"System Cache Mode has changed."
::= { iseTraps 171 }      --  1.3.6.1.4.1.2366.6.1.2.3.4.171

fanMajorityFailure NOTIFICATION-TYPE
OBJECTS {iseName, isePhysicalLocation, celEventDescription, celFanId, celFanStatus }  
STATUS	current
DESCRIPTION
	"Two or more fans in the ISE have failed."
::= { iseTraps 177 }      --  1.3.6.1.4.1.2366.6.1.2.3.4.177

iseUninitialing NOTIFICATION-TYPE
OBJECTS {iseName, isePhysicalLocation, celEventDescription }  
STATUS	current
DESCRIPTION
	"ISE is being Uninitialized - Factory Reset."
::= { iseTraps 181 }      --  1.3.6.1.4.1.2366.6.1.2.3.4.181

iseWarmBoot NOTIFICATION-TYPE
OBJECTS {iseName, isePhysicalLocation, celEventDescription }  
STATUS	current
DESCRIPTION
	"Ise is being Warm Booted."
::= { iseTraps 182 }      --  1.3.6.1.4.1.2366.6.1.2.3.4.182

volumePresented NOTIFICATION-TYPE
OBJECTS {iseName, isePhysicalLocation, fwEventDescription }  
STATUS	current
DESCRIPTION
	"Volume Presented to Host."
::= { iseTraps 231 }      --  1.3.6.1.4.1.2366.6.1.2.3.4.231

volumeUnpresented NOTIFICATION-TYPE
OBJECTS {iseName, isePhysicalLocation, fwEventDescription }  
STATUS	current
DESCRIPTION
	"Volume Unpresented from Host."
::= { iseTraps 232 }      --  1.3.6.1.4.1.2366.6.1.2.3.4.232

volumeAttributeChanged NOTIFICATION-TYPE
OBJECTS {iseName, isePhysicalLocation, fwEventDescription }  
STATUS	current
DESCRIPTION
	"An attribute on this Volume has been changed."
::= { iseTraps 233 }      --  1.3.6.1.4.1.2366.6.1.2.3.4.233

hbaAttributeChange NOTIFICATION-TYPE
OBJECTS {iseName, isePhysicalLocation, agentEventDescription  }  
STATUS	current
DESCRIPTION
	"An attribute of an HBA has been changed.  (Volume presents and unpresents)"
::= { iseTraps 234}      --  1.3.6.1.4.1.2366.6.1.2.3.4.234 

hbaCreated NOTIFICATION-TYPE
OBJECTS {iseName, isePhysicalLocation, agentEventDescription  }  
STATUS	current
DESCRIPTION
	"An HBA has been created."
::= { iseTraps 235}      --  1.3.6.1.4.1.2366.6.1.2.3.4.235 
	
hbaDeleted NOTIFICATION-TYPE
OBJECTS {iseName, isePhysicalLocation, agentEventDescription  }  
STATUS	current
DESCRIPTION
	"An HBA has been deleted."
::= { iseTraps 236}      --  1.3.6.1.4.1.2366.6.1.2.3.4.236 

parityScanStart NOTIFICATION-TYPE
OBJECTS {iseName, isePhysicalLocation, agentEventDescription  }  
STATUS	current
DESCRIPTION
	"Parity Scan Pass has started."
::= { iseTraps 250 }      --  1.3.6.1.4.1.2366.6.1.2.3.4.250 

parityScanEnd NOTIFICATION-TYPE
OBJECTS {iseName, isePhysicalLocation, agentEventDescription  }  
STATUS	current
DESCRIPTION
	"Parity Scan Pass has ended."
::= { iseTraps 251 }      --  1.3.6.1.4.1.2366.6.1.2.3.4.251

mrcError NOTIFICATION-TYPE
OBJECTS {iseName, isePhysicalLocation, agentEventDescription, celEventFruId, celMrcErrorCode  }  
STATUS	current
DESCRIPTION
	"MRC has an error"
::= { iseTraps 263}      --  1.3.6.1.4.1.2366.6.1.2.3.4.263 

dataPacError NOTIFICATION-TYPE
OBJECTS {iseName, isePhysicalLocation, agentEventDescription, celEventFruId, celDataPacErrorCode  }  
STATUS	current
DESCRIPTION
	"DataPac has an error"
::= { iseTraps 264}      --  1.3.6.1.4.1.2366.6.1.2.3.4.264

powerSupplyError NOTIFICATION-TYPE
OBJECTS {iseName, isePhysicalLocation, agentEventDescription, celEventFruId, celPowerSupplyErrorCode  }  
STATUS	current
DESCRIPTION
	"Power Supply has an error"
::= { iseTraps 265}      --  1.3.6.1.4.1.2366.6.1.2.3.4.265

fruOk NOTIFICATION-TYPE
OBJECTS {iseName, isePhysicalLocation, celEventDescription, celEventSubSystem, celEventSubSystemName, celEventSubSystemInstance }  
STATUS	current
DESCRIPTION
	"A FRU has returned to a healthy state."
::= { iseTraps 267 }      --  1.3.6.1.4.1.2366.6.1.2.3.4.267

volSfpTransmission NOTIFICATION-TYPE
OBJECTS {iseName, isePhysicalLocation, agentEventDescription, sfpId, sfpSignalState, sfpErrorCount  }  
STATUS	current
DESCRIPTION
	"Host FibreChannel Interface experienced/cleared a Transmission Fault on the interface"
::= { iseTraps 275}      --  1.3.6.1.4.1.2366.6.1.2.3.4.275

volBgInitEnd NOTIFICATION-TYPE
OBJECTS {iseName, isePhysicalLocation, agentEventDescription, celEventVolumeIndex  }  
STATUS	current
DESCRIPTION
	"Volume Background Init has ended"
::= { iseTraps 276}      --  1.3.6.1.4.1.2366.6.1.2.3.4.276

volBgInitStart NOTIFICATION-TYPE
OBJECTS {iseName, isePhysicalLocation, agentEventDescription, celEventVolumeIndex  }  
STATUS	current
DESCRIPTION
	"Volume Background Init has started"
::= { iseTraps 277}      --  1.3.6.1.4.1.2366.6.1.2.3.4.277

dataPacHealthWarning NOTIFICATION-TYPE
OBJECTS {iseName, isePhysicalLocation, agentEventDescription, celDataPacID, celDataPacStatus  }  
STATUS	current
DESCRIPTION
	"The Health of a DataPac has decreased to Warning"
::= { iseTraps 283}      --  1.3.6.1.4.1.2366.6.1.2.3.4.283 


sysCacheModeChange2WriteThru NOTIFICATION-TYPE
OBJECTS {iseName, isePhysicalLocation, agentEventDescription, celEventMrcId  }  
STATUS	current
DESCRIPTION
	"System Cache Mode has changed to Write-Through."
::= { iseTraps 285}      --  1.3.6.1.4.1.2366.6.1.2.3.4.285 

firmwareShutdown NOTIFICATION-TYPE
OBJECTS {iseName, isePhysicalLocation, agentEventDescription, celEventMrcId  }  
STATUS	current
DESCRIPTION
	"Shutdown of Firmware components as part of ISE Shutdown."
::= { iseTraps 363 }      --  1.3.6.1.4.1.2366.6.1.2.3.4.363 

mrcShutdown NOTIFICATION-TYPE
OBJECTS {iseName, isePhysicalLocation, agentEventDescription, celEventMrcId  }  
STATUS	current
DESCRIPTION
	"A single MRC is shutting down.  Partner MRC will hot boot and become the XO"
::= { iseTraps 364 }      --  1.3.6.1.4.1.2366.6.1.2.3.4.364

crashDumpWritten NOTIFICATION-TYPE
OBJECTS {iseName, isePhysicalLocation, agentEventDescription  }  
STATUS	current
DESCRIPTION
	"A new Crash Dump has been written to the SMLD and is now available."
::= { iseTraps 402 }      --  1.3.6.1.4.1.2366.6.1.2.3.4.402

mrcRedundancyLost NOTIFICATION-TYPE
OBJECTS {iseName, isePhysicalLocation, agentEventDescription, redundancyLostReasonCode }  
STATUS	current
DESCRIPTION
	"MRC Redundancy Lost."
::= { iseTraps 422 }      --  1.3.6.1.4.1.2366.6.1.2.3.4.422

mrcRedundancyRestored NOTIFICATION-TYPE
OBJECTS {iseName, isePhysicalLocation, agentEventDescription, celEventMrcId, celEventMrcId, restoredMrcIpAddress,reportingMrcIpAddress }  
STATUS	current
DESCRIPTION
	"MRC Redundancy Restored."
::= { iseTraps 423 }      --  1.3.6.1.4.1.2366.6.1.2.3.4.423

mrcMaintenanceBoot NOTIFICATION-TYPE
OBJECTS {iseName, isePhysicalLocation, agentEventDescription, celEventMrcId }  
STATUS	current
DESCRIPTION
	"MRC has booted in Maintenance Mode."
::= { iseTraps 426 }      --  1.3.6.1.4.1.2366.6.1.2.3.4.426

dataPacHandleOpen NOTIFICATION-TYPE
OBJECTS {iseName, isePhysicalLocation, agentEventDescription, celDataPacID }  
STATUS	current
DESCRIPTION
	"Datapac handle has been left open.  An unsecured datapac handle may prevent the ISE from protecting the datapac against improper removal."
::= { iseTraps 429 }      --  1.3.6.1.4.1.2366.6.1.2.3.4.429

celWrapImminent NOTIFICATION-TYPE
OBJECTS {iseName, isePhysicalLocation, celEventDescription }  
STATUS	current
DESCRIPTION
	"The CEL is 95 percent full and will begin wrapping events soon. Download the CEL to preserve older events."
::= { iseTraps 461 }      --  1.3.6.1.4.1.2366.6.1.2.3.4.461

snapshotPrepareComplete NOTIFICATION-TYPE
OBJECTS {iseName, isePhysicalLocation, agentEventDescription, celEventVolumeIndex, celEventVolumeName, celEventVolumeIndex, celEventVolumeName, celEventVolumeSnapshotType, celEventVolumeRaidType, celEventVolumeCacheMode, celEventVolumePoolId, celCcsOperationStatus }  
STATUS	current
DESCRIPTION
	"A Primary Volume has been prepared for a Snapshot - it will remain in write-through mode until the Snapshot is created."
::= { iseTraps 455 }      --  1.3.6.1.4.1.2366.6.1.2.3.4.455

snapshotCreateComplete NOTIFICATION-TYPE
OBJECTS {iseName, isePhysicalLocation, agentEventDescription, celEventVolumeIndex, celEventVolumeName, celEventVolumeIndex, celEventVolumeName, celEventVolumeSnapshotType, celCcsOperationStatus }  
STATUS	current
DESCRIPTION
	"A Snapshot volume creation is complete. Vars: Snapshot Vol Index, Snapshot Name, Primary vol Index, Primary Name."
::= { iseTraps 456 }      --  1.3.6.1.4.1.2366.6.1.2.3.4.456

primaryVolumeInWriteThrough NOTIFICATION-TYPE
OBJECTS {iseName, isePhysicalLocation, agentEventDescription, celEventVolumeIndex, celEventVolumeName, celEventVolumeIndex, celEventVolumeName }  
STATUS	current
DESCRIPTION
	"A Primary Volume has been prepared for a Snapshot and is in write-through mode until the Snapshot is created. Vars: Snapshot Vol Index, Snapshot Name, Primary vol Index, Primary Name."
::= { iseTraps 457 }      --  1.3.6.1.4.1.2366.6.1.2.3.4.457

volumeSizeChanged NOTIFICATION-TYPE
OBJECTS {iseName, isePhysicalLocation, agentEventDescription, celEventVolumeIndex, celEventVolumeName, celEventVolumeSize, celEventVolumeSize, celCcsOperationStatus }  
STATUS	current
DESCRIPTION
	"The size of a Volume has changed."
::= { iseTraps 469 }      --  1.3.6.1.4.1.2366.6.1.2.3.4.469

dataPacHealthEvent  NOTIFICATION-TYPE
OBJECTS {iseName, isePhysicalLocation, agentEventDescription, celDataPacID,  spotLocation, dataPacHealth }  
STATUS	current
DESCRIPTION
	"The Health of a DataPac has occurred."
::= { iseTraps 474 }      --  1.3.6.1.4.1.2366.6.1.2.3.4.474

dataPacHealthIncrease  NOTIFICATION-TYPE
OBJECTS {iseName, isePhysicalLocation, agentEventDescription, celDataPacID,  spotLocation, dataPacHealth }  
STATUS	current
DESCRIPTION
	"The Health of a DataPac has increased."
::= { iseTraps 475 }      --  1.3.6.1.4.1.2366.6.1.2.3.4.475

dataPacInoperative  NOTIFICATION-TYPE
OBJECTS {iseName, isePhysicalLocation, agentEventDescription, celDataPacID, spotLocation, dataPacHealth }  
STATUS	current
DESCRIPTION
	"A DataPac has gone into an Inoperative state."
::= { iseTraps 476 }      --  1.3.6.1.4.1.2366.6.1.2.3.4.476

sfpError  NOTIFICATION-TYPE
OBJECTS {iseName, isePhysicalLocation, agentEventDescription, sfpId, sfpErrorCode  }  
STATUS	current
DESCRIPTION
	"An error has been detected in the SFP (small form-factor pluggable.)"
::= { iseTraps 485 }      --  1.3.6.1.4.1.2366.6.1.2.3.4.485

dataPacMismatchConfig  NOTIFICATION-TYPE
OBJECTS {iseName, isePhysicalLocation, agentEventDescription, celDataPacID, fruSerialNum, fruSerialNum }  
STATUS	current
DESCRIPTION
	"DataPac configuration is detected to be Mismatched."
::= { iseTraps 490 }      --  1.3.6.1.4.1.2366.6.1.2.3.4.490

dataPacForeignCacheData  NOTIFICATION-TYPE
OBJECTS {iseName, isePhysicalLocation, agentEventDescription, celDataPacID, fruSerialNum }  
STATUS	current
DESCRIPTION
	"A DataPac is foreign and the cache data may not have been flushed."
::= { iseTraps 491 }      --  1.3.6.1.4.1.2366.6.1.2.3.4.491

dataPacForeignMrcCacheData  NOTIFICATION-TYPE
OBJECTS {iseName, isePhysicalLocation, agentEventDescription, celDataPacID, fruSerialNum }  
STATUS	current
DESCRIPTION
	"A DataPac is foreign and one or more MRC's has unflushed cache data."
::= { iseTraps 492 }      --  1.3.6.1.4.1.2366.6.1.2.3.4.492

mrcFwRevMismatch  NOTIFICATION-TYPE
OBJECTS {iseName, isePhysicalLocation, agentEventDescription, celEventMrcId, mrcFwRev, displayCrdFwRev, mrcCorrectFwRev }  
STATUS	current
DESCRIPTION
	"Firmware revision of the MRC is mismatched with the revision of the Display Card."
::= { iseTraps 493 }      --  1.3.6.1.4.1.2366.6.1.2.3.4.493

iseSystemMaintenanceMode  NOTIFICATION-TYPE
OBJECTS {iseName, isePhysicalLocation, agentEventDescription, mrcMaintModeFlags, mrcMaintModeFlagsString, mrcInoperativeModeCode, mrcInoperativeModeCodeString, mrcDiagUtilModeCode, mrcDiagUtilModeCodeString }  
STATUS	current
DESCRIPTION
	"ISE is in system maintenance mode."
::= { iseTraps 494 }      --  1.3.6.1.4.1.2366.6.1.2.3.4.494

cacheMaintenanceMode NOTIFICATION-TYPE
OBJECTS {iseName, isePhysicalLocation, agentEventDescription, celEventMrcId, mrcGenerationNum, dataPacGenerationNum }  
STATUS	current
DESCRIPTION
	"The cache state of the MRC does not match the cache state of the DataPacs."
::= { iseTraps 495 }      --  1.3.6.1.4.1.2366.6.1.2.3.4.495

mrcInvalid  NOTIFICATION-TYPE
OBJECTS {iseName, isePhysicalLocation, agentEventDescription, celEventMrcId }  
STATUS	current
DESCRIPTION
	"An MRC is foreign with unflushed cache data in the DataPacs."
::= { iseTraps 497 }      --  1.3.6.1.4.1.2366.6.1.2.3.4.497

unsupportedMetaVersion NOTIFICATION-TYPE
OBJECTS {iseName, isePhysicalLocation, agentEventDescription, celEventMrcId, currentVersion, supportedVersion }  
STATUS	current
DESCRIPTION
	"The overall metadata version is not supported by this firmware version."
::= { iseTraps 506 }      --  1.3.6.1.4.1.2366.6.1.2.3.4.506

unsupportedVpdVersion NOTIFICATION-TYPE
OBJECTS {iseName, isePhysicalLocation, agentEventDescription, celEventMrcId, celEventSubSystemName, celEventSubSystemInstance, currentVersion, supportedVersion }  
STATUS	current
DESCRIPTION
	"Current VPD version is unsupported by the MRC."
::= { iseTraps 507 }      --  1.3.6.1.4.1.2366.6.1.2.3.4.507

displayCardError NOTIFICATION-TYPE
OBJECTS {iseName, isePhysicalLocation, agentEventDescription, celEventFruId, celDispCardErrorCode  }  
STATUS	current
DESCRIPTION
	"Display Card has an error"
::= { iseTraps 512}      --  1.3.6.1.4.1.2366.6.1.2.3.4.512

mrcOtherDisabled  NOTIFICATION-TYPE
OBJECTS {iseName, isePhysicalLocation, agentEventDescription, celEventMrcId }  
STATUS	current
DESCRIPTION
	"MRC (other) has been disabled - booting into single MRC Mode."
::= { iseTraps 514 }      --  1.3.6.1.4.1.2366.6.1.2.3.4.514

mrcAddedReboot  NOTIFICATION-TYPE
OBJECTS {iseName, isePhysicalLocation, agentEventDescription, celEventMrcId }  
STATUS	current
DESCRIPTION
	"The ISE has rebooted after an MRC was Added."
::= { iseTraps 516 }      --  1.3.6.1.4.1.2366.6.1.2.3.4.516

dataPacRemoveStarted  NOTIFICATION-TYPE
OBJECTS {iseName, isePhysicalLocation, agentEventDescription, celDataPacID }  
STATUS	current
DESCRIPTION
	"A DataPac Remove operation has started."
::= { iseTraps 520 }      --  1.3.6.1.4.1.2366.6.1.2.3.4.520

dataPacAddStarted  NOTIFICATION-TYPE
OBJECTS {iseName, isePhysicalLocation, agentEventDescription, celDataPacID }  
STATUS	current
DESCRIPTION
	"A DataPac Add operation has started."
::= { iseTraps 522 }      --  1.3.6.1.4.1.2366.6.1.2.3.4.522

volumeMigrateRequest NOTIFICATION-TYPE
OBJECTS {iseName, isePhysicalLocation, agentEventDescription, celEventVolumeIndex, celEventVolumeName, volumeGuidString}  
STATUS	current
DESCRIPTION
	"Data Synchronization for a remote volume was requested."
::= { iseTraps 532 }      --  1.3.6.1.4.1.2366.6.1.2.3.4.532


volumeMigrateStarted NOTIFICATION-TYPE
OBJECTS {iseName, isePhysicalLocation, agentEventDescription, celEventVolumeIndex, celEventVolumeName, volumeGuidString}  
STATUS	current
DESCRIPTION
	"Data Synchronization for a remote volume has begun."
::= { iseTraps 536 }      --  1.3.6.1.4.1.2366.6.1.2.3.4.536


volumeMigrateEnded NOTIFICATION-TYPE
OBJECTS {iseName, isePhysicalLocation, agentEventDescription, celEventVolumeIndex, celEventVolumeName, volumeGuidString}  
STATUS	current
DESCRIPTION
	"Data Synchronization for a remote volume has ended."
::= { iseTraps 537 }      --  1.3.6.1.4.1.2366.6.1.2.3.4.537


vpdLoadError NOTIFICATION-TYPE
OBJECTS {iseName, isePhysicalLocation, agentEventDescription, celEventMrcId, celEventSubSystem, celEventSubSystemName, celEventSubSystemInstance, vpdReasonCode}  
STATUS	current
DESCRIPTION
	"The specified VPD had an error and could not be loaded."
::= { iseTraps 556 }      --  1.3.6.1.4.1.2366.6.1.2.3.4.556

-- ****************** CEL_VMirrorInitDone  **********************   EEN_CCS_VMIRROR_INIT_DONE       601
vmirrorInitDone NOTIFICATION-TYPE
OBJECTS {iseName, isePhysicalLocation, agentEventDescription, vmirrorGuidString, vmirrorSize, vmirrorOpStatusCode }  
STATUS	current
DESCRIPTION
	"A VMirror Initialization request has been processed."
::= { iseTraps 601 }      --  1.3.6.1.4.1.2366.6.1.2.3.4.601

-- ****************** CEL_VMirrorMemberInitDone  ****************   EEN_CCS_VMIRROR_MEMBER_INIT_DONE       602
vmirrorMemberInitDone NOTIFICATION-TYPE
OBJECTS {iseName, isePhysicalLocation, agentEventDescription, vmirrorGuidString, mirrorIndex, mirrorMemberIndex, celCcsOperationStatus }  
STATUS	current
DESCRIPTION
	"An ISE Mirror Member Creation request completed."
::= { iseTraps 602 }      --  1.3.6.1.4.1.2366.6.1.2.3.4.602

-- ****************** CEL_VMirrorBreakDone  **********************   EEN_CCS_VMIRROR_BREAK_DONE       603
vmirrorBreakDone NOTIFICATION-TYPE
OBJECTS {iseName, isePhysicalLocation, agentEventDescription, vmirrorGuidString, vmirrorOpStatusCode }  
STATUS	current
DESCRIPTION
	"A VMirror Break request has been processed."
::= { iseTraps 603 }      --  1.3.6.1.4.1.2366.6.1.2.3.4.603


-- ****************** CEL_VMirrorMemberBreakDone  ***************   EEN_CCS_VMIRROR_MEMBER_BREAK_DONE       604
vmirrorMemberBreakDone NOTIFICATION-TYPE
OBJECTS {iseName, isePhysicalLocation, agentEventDescription, vmirrorGuidString, mirrorIndex, mirrorMemberIndex, celCcsOperationStatus }  
STATUS	current
DESCRIPTION
	"An ISE Mirror Member Break request completed."
::= { iseTraps 604 }      --  1.3.6.1.4.1.2366.6.1.2.3.4.604


-- ****************** CEL_VMirrorSetAttribute  ***************   EEN_CCS_VMIRROR_SET_ATTR       605
vmirrorAttributeChange NOTIFICATION-TYPE
OBJECTS {iseName, isePhysicalLocation, agentEventDescription, vmirrorGuidString, mirrorChangeMask }  
STATUS	current
DESCRIPTION
	"An Attribute of a Mirror has changed."
::= { iseTraps 605 }      --  1.3.6.1.4.1.2366.6.1.2.3.4.605


-- ****************** CEL_VMirrorStateChange  **********************   EEN_CCS_VMIRROR_EVENT_NOTIFICATION   610
vmirrorStateChange NOTIFICATION-TYPE
OBJECTS {iseName, isePhysicalLocation, agentEventDescription, vmirrorEventCode, vmirrorGuidString, volumeGuidString }  
STATUS	current
DESCRIPTION
	"A VMirror State Change has occurred."
::= { iseTraps 610 }      --  1.3.6.1.4.1.2366.6.1.2.3.4.610

-- ****************** CEL_IseInitWarning  ********************   EEN_CCS_ISE_INIT_WARNING         639
iseInitWarning NOTIFICATION-TYPE
OBJECTS {iseName, isePhysicalLocation, agentEventDescription, celEventSubSystemInstance, dataPacHealth }  
STATUS	current
DESCRIPTION
	"ISE was initialized with a reduced health DataPac."
::= { iseTraps 639 }      --  1.3.6.1.4.1.2366.6.1.2.3.4.639

-- ****************** CEL_AllMirrorsSynched  ********************   EEN_CCS_VMIRROR_ALL_SYNCHRONIZED       666
vmirrorSynchComplete NOTIFICATION-TYPE
OBJECTS {iseName, isePhysicalLocation, agentEventDescription }  
STATUS	current
DESCRIPTION
	"All VMirrors have completed synchronization."
::= { iseTraps 666 }      --  1.3.6.1.4.1.2366.6.1.2.3.4.666

-- ****************** CEL_Ise2IseNetDown  **********************   EEN_HIS_ISE_TO_ISE_ETHERNET_DOWN  674
ise2iseNetworkDown NOTIFICATION-TYPE
OBJECTS {iseName, isePhysicalLocation, agentEventDescription }  
STATUS	current
DESCRIPTION
	"ISE to ISE network connection is down.  VMirror function is impacted."
::= { iseTraps 674 }      --  1.3.6.1.4.1.2366.6.1.2.3.4.674

-- ****************** CEL_Ise2IseNetBack  **********************   EEN_HIS_ISE_TO_ISE_ETHERNET_BACK  675
ise2iseNetworkBack NOTIFICATION-TYPE
OBJECTS {iseName, isePhysicalLocation, agentEventDescription }  
STATUS	current
DESCRIPTION
	"ISE to ISE network connection has returned."
::= { iseTraps 675 }      --  1.3.6.1.4.1.2366.6.1.2.3.4.675

-- ****************** CEL_DriveCodeUpdateEnd  *******************   EEN_CCS_DRIVE_CODE_MDA_UPDATE_END      677
driveCodeUpdateEnd NOTIFICATION-TYPE
OBJECTS {iseName, isePhysicalLocation, agentEventDescription, celDataPacID, celCcsOperationStatus }  
STATUS	current
DESCRIPTION
	"Datapac/Drive code update has completed.  Check Op Status for final result."
::= { iseTraps 677 }      --  1.3.6.1.4.1.2366.6.1.2.3.4.677

--  ****************** CEL_SuperCapLowOnBoot  *******************   EEN_ENC_SUPERCAP_LOW_ON_BOOT      687
superCapLowOnBoot NOTIFICATION-TYPE
OBJECTS {iseName, isePhysicalLocation, agentEventDescription, superCapId, superCapVoltage }  
STATUS	current
DESCRIPTION
	"SuperCap Voltage is low on cold boot.  Ise will pause the boot process until the charge level is sufficient."
::= { iseTraps 687 }      --  1.3.6.1.4.1.2366.6.1.2.3.4.687

--  ****************** CEL_SuperCapVoltageRestored  *******************   EEN_ENC_SUPERCAP_RESTORED   688
superCapVoltageRestored NOTIFICATION-TYPE
OBJECTS {iseName, isePhysicalLocation, agentEventDescription, superCapId }  
STATUS	current
DESCRIPTION
	"SuperCap Voltage has been restored to a sufficient level."
::= { iseTraps 688 }      --  1.3.6.1.4.1.2366.6.1.2.3.4.688

--  ****************** CEL_SuperCapLowReboot  *******************   EEN_ENC_SUPERCAP_LOW_REBOOT       689
superCapLowReboot NOTIFICATION-TYPE
OBJECTS {iseName, isePhysicalLocation, agentEventDescription, superCapId, superCapVoltage }  
STATUS	current
DESCRIPTION
	"SuperCap Voltage level is low and the ISE2 will cold boot to protect the system cache."
::= { iseTraps 689 }      --  1.3.6.1.4.1.2366.6.1.2.3.4.689

--  ****************** CEL_SuperCapError  ************************   EEN_ENC_SUPERCAP_ERROR           691
superCapError NOTIFICATION-TYPE
OBJECTS {iseName, isePhysicalLocation, agentEventDescription, superCapId, superCapErrorBitmask}  
STATUS	current
DESCRIPTION
	"SuperCap Error detected.  Translate the error bitmask to determine the error
	    badRtc = 0x1
        inserted = 0x2
        removed = 0x4
        deadBeat = 0x8
        ableFault = 0x10
        badTemp = 0x20
        otherMrcReset = 0x40
        badVpdCookie = 0x80
        mrcNotPresent = 0x100
        badMrcOffline = 0x200
        badVpdCrc = 0x400
        badVpdType = 0x800
        badVpdVersion = 0x1000
        badVpd = 0x2000
        persistentFault = 0x8000"
::= { iseTraps 691 }      --  1.3.6.1.4.1.2366.6.1.2.3.4.691

--  ****************** CEL_MRCSingleMode  *******************   EEN_ENC_MRC_SINGLE   692
mrcRunningSingleMode NOTIFICATION-TYPE
OBJECTS {iseName, isePhysicalLocation, agentEventDescription, celEventMrcId }  
STATUS	current
DESCRIPTION
	"MRC is running in single mode even though the other MRC is present."
::= { iseTraps 692 }      --  1.3.6.1.4.1.2366.6.1.2.3.4.692

-- ****************** CEL_DriveKgWarning  *******************   EEN_CCS_DRIVE_KG_WARNING      698
driveKgWarning NOTIFICATION-TYPE
OBJECTS {iseName, isePhysicalLocation, agentEventDescription, celDataPacID, celDriveSpotLocation, dataPacHealth }  
STATUS	current
DESCRIPTION
	"DataPac health is reduced due to a drive redundancy preserved sparing state."
::= { iseTraps 698 }      --  1.3.6.1.4.1.2366.6.1.1.3.4.698

-- ****************** CEL_DetectPcieCrash  *******************   EEN_ER_CRASH_DETECT_PCIE_REDUCED  701

detectPcieCrash NOTIFICATION-TYPE
OBJECTS {iseName, isePhysicalLocation, agentEventDescription, celEventMrcId }  
STATUS	current
DESCRIPTION
	"Last crash caused to remediate the reduced capacity PCIE."
::= { iseTraps 701 }      --  1.3.6.1.4.1.2366.6.1.1.3.4.701


-- ****************** CEL_VMirrorMemberPause  ***************   EEN_DME_VMIRROR_MEMBER_PAUSE       734
vmirrorMemberPause NOTIFICATION-TYPE
OBJECTS {iseName, isePhysicalLocation, agentEventDescription, vmirrorGuidString, mirrorMemberIndex }  
STATUS	current
DESCRIPTION
	"A VMirror member has been marked as paused or busy."
::= { iseTraps 734 }      --  1.3.6.1.4.1.2366.6.1.2.3.4.734


-- ****************** CEL_VMirrorMemberResume  ***************   EEN_DME_VMIRROR_MEMBER_RESUME       735
vmirrorMemberResume NOTIFICATION-TYPE
OBJECTS {iseName, isePhysicalLocation, agentEventDescription, vmirrorGuidString, mirrorMemberIndex }  
STATUS	current
DESCRIPTION
	"A VMirror member has resumed."
::= { iseTraps 735 }      --  1.3.6.1.4.1.2366.6.1.2.3.4.735


-- ***************** CEL_Ise2WitnessEthernetBack  *************   EEN_HIS_ISE_TO_WITNESS_ETHERNET_BACK       738
ise2WitnessEthernetBack NOTIFICATION-TYPE
OBJECTS {iseName, isePhysicalLocation, agentEventDescription }  
STATUS	current
DESCRIPTION
	"Ethernet access betweeen ISE and Mirror Witness has been restored."
::= { iseTraps 738 }      --  1.3.6.1.4.1.2366.6.1.2.3.4.738


-- ***************** CEL_Ise2WitnessEthernetDown  *************   EEN_HIS_ISE_TO_WITNESS_ETHERNET_DOWN       739
ise2WitnessEthernetDown NOTIFICATION-TYPE
OBJECTS {iseName, isePhysicalLocation, agentEventDescription }  
STATUS	current
DESCRIPTION
	"The ISE to Mirror Witness Ethernet communication is down."
::= { iseTraps 739 }      --  1.3.6.1.4.1.2366.6.1.2.3.4.739


-- ***************** CEL_Ise2IseThruWitnessEthernetBack *******   EEN_HIS_ISE_TO_ISE_THRU_WITNESS_ETHERNET_BACK   740
ise2IseThruWitnessEthernetBack NOTIFICATION-TYPE
OBJECTS {iseName, isePhysicalLocation, agentEventDescription }  
STATUS	current
DESCRIPTION
	"Ethernet access betweeen ISEs through the Witness has been restored."
::= { iseTraps 740 }      --  1.3.6.1.4.1.2366.6.1.2.3.4.740


-- ***************** CEL_Ise2IseThruWitnessEthernetDown *******   EEN_HIS_ISE_TO_ISE_THRU_WITNESS_ETHERNET_DOWN   741
ise2IseThruWitnessEthernetDown NOTIFICATION-TYPE
OBJECTS {iseName, isePhysicalLocation, agentEventDescription }  
STATUS	current
DESCRIPTION
	"The ISE-to-ISE ethernet comm through the Mirror Witness path is down."
::= { iseTraps 741 }      --  1.3.6.1.4.1.2366.6.1.2.3.4.741


-- ***************** CEL_SplitBrainCorruption *******   EEN_DME_SPIT_BRAIN_DATA_CORRUPTION   745
mirrorSplitBrain NOTIFICATION-TYPE
OBJECTS {iseName, isePhysicalLocation, agentEventDescription, vmirrorGuidString, memberWrites, memberWrites }  
STATUS	current
DESCRIPTION
	"Number of writes for a Mirror member for a Mirror experiencing Split Brain."
::= { iseTraps 745 }      --  1.3.6.1.4.1.2366.6.1.2.3.4.745


-- ****************** CEL_DmePingLatency  *******************   EEN_DME_PING_LATENCY  746
mirrorPingLatency NOTIFICATION-TYPE
OBJECTS {iseName, isePhysicalLocation, agentEventDescription, currentLatency, averageLatency }  
STATUS	current
DESCRIPTION
	"Mirror Ping Latency is Excessive"
::= { iseTraps 746 }      --  1.3.6.1.4.1.2366.6.1.2.3.4.746

-- ****************** CEL_VsPoolThinThreshold  *****   EEN_VS_POOL_THIN_THRESHOLD  760
poolThinThreshold NOTIFICATION-TYPE
OBJECTS {iseName, isePhysicalLocation, agentEventDescription }  
STATUS	current
DESCRIPTION
	"Reached pool threshold for Thin Provisioning"
::= { iseTraps 760 }      --  1.3.6.1.4.1.2366.6.1.2.3.4.760

-- ****************** CEL_VsPoolOutOfSpace  *****   EEN_VS_POOL_OUT_OF_SPACE  761
poolOutOfSpace NOTIFICATION-TYPE
OBJECTS {iseName, isePhysicalLocation, agentEventDescription }  
STATUS	current
DESCRIPTION
	"Out of space in the pool for Thin Provisioned volumes"
::= { iseTraps 761 }      --  1.3.6.1.4.1.2366.6.1.2.3.4.761
-- 

-- *******************************************************************************************************
-- ********************************      Storage MGMT Traps      *****************************************
-- *******************************************************************************************************

hostCreated NOTIFICATION-TYPE
OBJECTS {iseName, isePhysicalLocation, agentEventDescription, agentEventHostName, agentEventHostIndex, agentEventHostOsType }  
STATUS	current
DESCRIPTION
	"Host Created."
::= { iseTraps 1321 }      --  1.3.6.1.4.1.2366.6.1.2.3.4.1321

hostDeleted NOTIFICATION-TYPE
OBJECTS {iseName, isePhysicalLocation, agentEventDescription, agentEventHostName, agentEventHostIndex, agentEventHostOsType }  
STATUS	current
DESCRIPTION
	"Host Deleted."
::= { iseTraps 1323 }      --  1.3.6.1.4.1.2366.6.1.2.3.4.1323

userLoggedIn NOTIFICATION-TYPE
OBJECTS {iseName, isePhysicalLocation, agentEventDescription, agentEventHttpIpAddress, agentEventUserName }  
STATUS	current
DESCRIPTION
	"A User has logged in."
::= { iseTraps 3001 }      --  1.3.6.1.4.1.2366.6.1.2.3.4.3001

systemSetupChange NOTIFICATION-TYPE
OBJECTS {iseName, isePhysicalLocation, agentEventDescription  }  
STATUS	current
DESCRIPTION
	"Current System Info, Network Configuration, or System Clock Settings have been changed by a User."
::= { iseTraps 3002 }      --  1.3.6.1.4.1.2366.6.1.2.3.4.3002

userRequestReformat NOTIFICATION-TYPE
OBJECTS {iseName, isePhysicalLocation, agentEventDescription }  
STATUS	current
DESCRIPTION
	"User requests ISE to be Reformated."
::= { iseTraps 3008 }      --  1.3.6.1.4.1.2366.6.1.2.3.4.3008
 
userRequestRestart  NOTIFICATION-TYPE
OBJECTS {iseName, isePhysicalLocation, agentEventDescription  }  
STATUS	current
DESCRIPTION
	"A User has requested the ISE to Restart."
::= { iseTraps 3010 }      --  1.3.6.1.4.1.2366.6.1.2.3.4.3010

userRequestShutdown NOTIFICATION-TYPE
OBJECTS {iseName, isePhysicalLocation, agentEventDescription  }  
STATUS	current
DESCRIPTION
	"ISE is shutting down per User Request."
::= { iseTraps 3011 }      --  1.3.6.1.4.1.2366.6.1.2.3.4.3011
 
snmpConfigChange NOTIFICATION-TYPE
OBJECTS {iseName, isePhysicalLocation, agentEventDescription  }  
STATUS	current
DESCRIPTION
	"The SNMP Configuration settings have been changed by a User."
::= { iseTraps 3012 }      --  1.3.6.1.4.1.2366.6.1.2.3.4.3012

passwordChanged  NOTIFICATION-TYPE
OBJECTS {iseName, isePhysicalLocation, agentEventDescription  }  
STATUS	current
DESCRIPTION
	"The System password has been changed."
::= { iseTraps 3016 }      --  1.3.6.1.4.1.2366.6.1.2.3.4.3016

mrcFwUpgradeStarted NOTIFICATION-TYPE
OBJECTS {iseName, isePhysicalLocation, agentEventDescription  }  
STATUS	current
DESCRIPTION
	"MRC Firmware Upgrade has Started."
::= { iseTraps 3019 }      --  1.3.6.1.4.1.2366.6.1.2.3.4.3019

mrcFwUpgradeComplete NOTIFICATION-TYPE
OBJECTS {iseName, isePhysicalLocation, agentEventDescription  }  
STATUS	current
DESCRIPTION
	"MRC Firmware Upgrade has Completed."
::= { iseTraps 3020 }      --  1.3.6.1.4.1.2366.6.1.2.3.4.3020

mrcFwCommitInvoked NOTIFICATION-TYPE
OBJECTS {iseName, isePhysicalLocation, agentEventDescription  }  
STATUS	current
DESCRIPTION
	"MRC Firmware Commit has been Invoked ."
::= { iseTraps 3021 }      --  1.3.6.1.4.1.2366.6.1.2.3.4.3021

mrcFwCommitComplete NOTIFICATION-TYPE
OBJECTS {iseName, isePhysicalLocation, agentEventDescription  }  
STATUS	current
DESCRIPTION
	"MRC Firmware Commit has Completed."
::= { iseTraps 3022 }      --  1.3.6.1.4.1.2366.6.1.2.3.4.3022

mrcFwCommitCancelInvoked NOTIFICATION-TYPE
OBJECTS {iseName, isePhysicalLocation, agentEventDescription  }  
STATUS	current
DESCRIPTION
	"MRC Firmware Commit Cancel has been Invoked."
::= { iseTraps 3023 }      --  1.3.6.1.4.1.2366.6.1.2.3.4.3023

mrcFwCommitCancelComplete  NOTIFICATION-TYPE
OBJECTS {iseName, isePhysicalLocation, agentEventDescription  }  
STATUS	current
DESCRIPTION
	"MRC Firmware Commit Cancel has Completed."
::= { iseTraps 3024 }      --  1.3.6.1.4.1.2366.6.1.2.3.4.3024
 
dataPacFwUpgradeStarted NOTIFICATION-TYPE
OBJECTS {iseName, isePhysicalLocation, agentEventDescription  }  
STATUS	current
DESCRIPTION
	"DataPac Firmware Upgrade has started."
::= { iseTraps 3036 }      --  1.3.6.1.4.1.2366.6.1.2.3.4.3036

dataPacFwUpgradeComplete NOTIFICATION-TYPE
OBJECTS {iseName, isePhysicalLocation, agentEventDescription  }  
STATUS	current
DESCRIPTION
	"DataPac Firmware Upgrade has Completed."
::= { iseTraps 3037 }      --  1.3.6.1.4.1.2366.6.1.2.3.4.3037

fwFileNotValid NOTIFICATION-TYPE
OBJECTS {iseName, isePhysicalLocation, agentEventDescription  }  
STATUS	current
DESCRIPTION
	"The Firmware File that was uploaded is not valid."
::= { iseTraps 3040 }      --  1.3.6.1.4.1.2366.6.1.2.3.4.3040

fwFileUploadFailed NOTIFICATION-TYPE
OBJECTS {iseName, isePhysicalLocation, agentEventDescription  }  
STATUS	current
DESCRIPTION
	"Firmware File Upload Failed."
::= { iseTraps 3041 }      --  1.3.6.1.4.1.2366.6.1.2.3.4.3041

dataPacFwUpgradeFailed NOTIFICATION-TYPE
OBJECTS {iseName, isePhysicalLocation, agentEventDescription  }  
STATUS	current
DESCRIPTION
	"DataPac Firmware Upgrade has Failed"
::= { iseTraps 3042}      --  1.3.6.1.4.1.2366.6.1.2.3.4.3042

mrcFwUpgradeFailed NOTIFICATION-TYPE
OBJECTS {iseName, isePhysicalLocation, agentEventDescription, fwUpgradeFailedCode  }  
STATUS	current
DESCRIPTION
	"MRC Firmware Upgrade has Failed - see agentEventDescription for details."
::= { iseTraps 3043 }      --  1.3.6.1.4.1.2366.6.1.2.3.4.3043

userDataPacAdd NOTIFICATION-TYPE
OBJECTS {iseName, isePhysicalLocation, agentEventDescription  }  
STATUS	current
DESCRIPTION
	"User requests a DataPac to be Added."
::= { iseTraps 3044 }      --  1.3.6.1.4.1.2366.6.1.2.3.4.3044

userDataPacRemove NOTIFICATION-TYPE
OBJECTS {iseName, isePhysicalLocation, agentEventDescription  }  
STATUS	current
DESCRIPTION
	"User requests a DataPac to be Removed."
::= { iseTraps 3045 }      --  1.3.6.1.4.1.2366.6.1.2.3.4.3045

userMrcAdd NOTIFICATION-TYPE
OBJECTS {iseName, isePhysicalLocation, agentEventDescription  }  
STATUS	current
DESCRIPTION
	"User requests an MRC to be Added."
::= { iseTraps 3047 }      --  1.3.6.1.4.1.2366.6.1.2.3.4.3047

userMrcRemove NOTIFICATION-TYPE
OBJECTS {iseName, isePhysicalLocation, agentEventDescription  }  
STATUS	current
DESCRIPTION
	"User requests an MRC to be Removed."
::= { iseTraps 3048 }      --  1.3.6.1.4.1.2366.6.1.2.3.4.3048

generalUpdateSent NOTIFICATION-TYPE
OBJECTS {iseName, isePhysicalLocation, agentEventDescription  }  
STATUS	current
DESCRIPTION
	"Active Watch General Update Sent."
::= { iseTraps 3049 }      --  1.3.6.1.4.1.2366.6.1.2.3.4.3049

telemetryStarted NOTIFICATION-TYPE
OBJECTS {iseName, isePhysicalLocation, agentEventDescription  }  
STATUS	current
DESCRIPTION
	"Active Watch General Telemetry Started."
::= { iseTraps 3051 }      --  1.3.6.1.4.1.2366.6.1.1.3.4.3051

telemetrySent NOTIFICATION-TYPE
OBJECTS {iseName, isePhysicalLocation, agentEventDescription  }  
STATUS	current
DESCRIPTION
	"Active Watch Telemetry Sent."
::= { iseTraps 4001 }      --  1.3.6.1.4.1.2366.6.1.2.3.4.4001

awSubscriptionAdded NOTIFICATION-TYPE
OBJECTS {iseName, isePhysicalLocation, agentEventDescription  }  
STATUS	current
DESCRIPTION
	"Active Watch Subscription Added."
::= { iseTraps 3053 }      --  1.3.6.1.4.1.2366.6.1.2.3.4.3053

awSubscriptionModified NOTIFICATION-TYPE
OBJECTS {iseName, isePhysicalLocation, agentEventDescription  }  
STATUS	current
DESCRIPTION
	"Active Watch Subscription Modified."
::= { iseTraps 3054 }      --  1.3.6.1.4.1.2366.6.1.2.3.4.3054

awSubscriptionDeleted NOTIFICATION-TYPE
OBJECTS {iseName, isePhysicalLocation, agentEventDescription  }  
STATUS	current
DESCRIPTION
	"Active Watch Subscription Deleted."
::= { iseTraps 3055 }      --  1.3.6.1.4.1.2366.6.1.2.3.4.3055


-- *********************   Compliance statement for notifications  **********************

iseNotificationGroup   NOTIFICATION-GROUP
   NOTIFICATIONS {
                    agentEventTrap,
                    fwEventTrap,
                    celEventTrap,
                    storagePoolDeleted,
                    iseInited,
                    storagePoolInited,
                    volumeCreated,
                    volumeDeleted,
                    volumeInoperative,
                    systemShuttingDown,
                    mrcInserted,
                    dataPacRemoved,
                    dataPacAdded,
                    driveCodeUpdated,
                    fruCriticalTemp,
                    fruWarningTemp,
                    fruRemovalInsertion,
                    fruNormalTemp,
                    mrcRemovedHotBoot,
                    mrcRemovedColdBoot,
                    systemInoperativeColdBoot,
                    mrcOfflineColdBoot,
                    cacheModeChange,
                    fanMajorityFailure,
                    iseUninitialing,
                    iseWarmBoot,
                    volumePresented,
                    volumeUnpresented,
                    volumeAttributeChanged,                    
                    hbaAttributeChange,
                    hbaCreated,
                    hbaDeleted,
                    parityScanStart,
                    parityScanEnd,
                    mrcError,
                    dataPacError,
                    powerSupplyError,
                    displayCardError,
                    fruOk,
                    volSfpTransmission,
                    volBgInitEnd,
                    volBgInitStart,
                    dataPacHealthWarning,
                    sysCacheModeChange2WriteThru,
                    firmwareShutdown,
                    mrcShutdown,
                    crashDumpWritten,
                    mrcRedundancyLost,
                    mrcRedundancyRestored,
                    mrcMaintenanceBoot,
                    dataPacHandleOpen,
                    celWrapImminent,
                    snapshotPrepareComplete,
                    snapshotCreateComplete,
                    primaryVolumeInWriteThrough,
                    volumeSizeChanged,
                    dataPacHealthEvent,
                    dataPacHealthIncrease,
                    dataPacInoperative,
                    sfpError,
                    dataPacMismatchConfig,
                    dataPacForeignCacheData,
                    dataPacForeignMrcCacheData,
                    mrcFwRevMismatch,
                    iseSystemMaintenanceMode,
                    cacheMaintenanceMode,
                    mrcInvalid,
                    unsupportedMetaVersion,
                    unsupportedVpdVersion,
                    mrcOtherDisabled,
                    mrcAddedReboot,
                    dataPacRemoveStarted,
                    dataPacAddStarted,
                    volumeMigrateRequest,
                    volumeMigrateStarted,
                    volumeMigrateEnded,
                    vpdLoadError,
                    vmirrorInitDone,
                    vmirrorMemberInitDone,
                    vmirrorBreakDone,
                    vmirrorMemberBreakDone,
                    vmirrorAttributeChange,
                    vmirrorStateChange,
                    iseInitWarning,
                    vmirrorSynchComplete,
                    ise2iseNetworkDown,
                    ise2iseNetworkBack,
                    driveCodeUpdateEnd,
                    superCapLowOnBoot,
                    superCapVoltageRestored,
                    superCapLowReboot,
                    superCapError,
                    mrcRunningSingleMode,
                    driveKgWarning,
                    detectPcieCrash,
                    vmirrorMemberPause,
                    vmirrorMemberResume,
                    ise2WitnessEthernetBack,
                    ise2WitnessEthernetDown,
                    ise2IseThruWitnessEthernetBack,
                    ise2IseThruWitnessEthernetDown,
                    mirrorSplitBrain,
                    mirrorPingLatency,
                    poolThinThreshold,
                    poolOutOfSpace,
                    
-- ***************  MGMT Traps  *******************                   
                    hostCreated,
                    hostDeleted,
                    userLoggedIn,
                    systemSetupChange,
                    userRequestReformat,
                    userRequestRestart,
                    userRequestShutdown,
                    snmpConfigChange,
                    passwordChanged,
                    mrcFwUpgradeStarted,
                    mrcFwUpgradeComplete,
                    mrcFwCommitInvoked,
                    mrcFwCommitComplete,
                    mrcFwCommitCancelInvoked,
                    mrcFwCommitCancelComplete,
                    dataPacFwUpgradeStarted,
                    dataPacFwUpgradeComplete,
                    fwFileNotValid,
                    fwFileUploadFailed,
                    dataPacFwUpgradeFailed,
                    mrcFwUpgradeFailed,
                    userDataPacAdd,
                    userDataPacRemove,
                    userMrcAdd,
                    userMrcRemove,
                    generalUpdateSent,
                    telemetryStarted,
                    telemetrySent,
                    awSubscriptionAdded,
                    awSubscriptionModified,
                    awSubscriptionDeleted                                                                                                                                                                                                 
		      }
    STATUS       current
    DESCRIPTION "A collection of ise Notifications"
    ::= { iseMIBGroups 9 }
             

END
